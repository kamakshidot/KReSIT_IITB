FME workspace kresit_ifc.fmw

Parameters:
- OutputFolder = D:\drp\trial\DCR-LOD_100   # Select an output folder
- DestDataset_GML_3 = C:\_Development\GitHub\ifc-to-citygml3\output\FZK-Haus_CityGML3.gml   # Destination Geography Markup Language (GML) File
- SourceDataset_REVIT = C:\_Development\GitHub\ifc-to-citygml3\input\AC20-FZK-Haus.ifc   # Source Revit Export File(s)
- SourceDataset_IFC = C:\_Development\GitHub\ifc-to-citygml3\input\AC20-FZK-Haus.ifc   # Source Industry Foundation Class (IFC) File(s)

Readers:
- IFC_1: IFC from $(SourceDataset_IFC)
- REVIT_1: REVIT from $(SourceDataset_REVIT) in EPSG:31467

Writers:
- GML_1: GML to $(DestDataset_GML_3) in EPSG:31467

AttributeReprojector
    DEST = EPSG:31467
    SOURCE = LL-WGS84
    XATTR = RefLongitude
    YATTR = RefLatitude
    -> FeatureMerger_4 [SUPPLIER]
FeatureMerger_8
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> Building (writer GML_1)
AttributeKeeper_3
    CREATE_BULK_MODE_FEATURES = No
    KEEP_ATTRS = GlobalId
    -> FeatureMerger_4 [REQUESTOR]
FeatureMerger_4
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> 3DAffiner_8
3DAffiner_8
    A = 1
    B = 0
    C = 0
    D = @Value(RefLongitude)
    E = 0
    F = 1
    G = 0
    H = @Value(RefLatitude)
    I = 0
    J = 0
    K = 1
    L = @Value(RefElevation)
    AFFINED -> FeatureTypeFilter_2
FeatureTypeFilter_2
    ATTRIBUTES = Site,Wall,Beam,Slab,Member,Railing,Stair,Space,Window,Door,<Unfiltered>,<Blank>
    Wall -> FeatureMerger_7 [REQUESTOR]
    Beam -> FeatureMerger_7 [REQUESTOR]
    Slab -> FeatureMerger_7 [REQUESTOR]
    Member -> FeatureMerger_7 [REQUESTOR]
    Railing -> FeatureMerger_15 [REQUESTOR]
    Stair -> FeatureMerger_15 [REQUESTOR]
    Space -> AttributeCreator_16
FeatureMerger_1
    ATTR_ACCUM_MODE = Merge Supplier
    ATTR_CONFLICT_RES = Use Requestor
    IGNORE_NULLS = No
    JOIN_KEYS = 1 1 AUTO
    MERGE_TYPE = Attributes Only
    PROCESS_DUPS = NO
    REJECT_NULL_MISSING_KEYS = No
    SUPPLIERS_FIRST = No
    MERGED -> FeatureTypeFilter
FeatureTypeFilter
    ATTRIBUTES = Wall,Beam,Slab,Member,Railing,Stair,Space,IfcBuildingStorey,<Unfiltered>,<Blank>
    Railing -> BuildingInstallation (writer GML_1)
    Stair -> BuildingInstallation (writer GML_1)
    Space -> BuildingRoom (writer GML_1)
    IfcBuildingStorey -> Storey (writer GML_1)

Bookmark: IFC Reader
IfcProject (reader IFC_1)
    attributes: GlobalId char(22), Name string, Description string, ObjectType string, LongName string, Phase string, Annotation geometry, Axis geometry, Body geometry, Box geometry, FootPrint geometry, ifc_type_object_id string
    -> AttributeRenamer_8
IfcSite (reader IFC_1)
    attributes: GlobalId char(22), Name string, Description string, ObjectType string, LongName string, CompositionType string, RefLatitude real, RefLongitude real, RefElevation real, LandTitleNumber string, SiteAddress.Purpose enumeration, SiteAddress.Description string, SiteAddress.UserDefinedPurpose varchar(255), SiteAddress.InternalLocation varchar(255), SiteAddress.AddressLines string, SiteAddress.PostalBox varchar(255), SiteAddress.Town varchar(255), SiteAddress.Region varchar(255), SiteAddress.PostalCode varchar(255), SiteAddress.Country varchar(255), Annotation geometry, Axis geometry, Body geometry, Box geometry, FootPrint geometry, ifc_type_object_id string
    -> AttributeReprojector
IfcWallStandardCase (reader IFC_1)
    attributes: GlobalId char(22), Name string, Description string, ObjectType string, Tag varchar(255), PredefinedType enumeration, Annotation geometry, Axis geometry, Body geometry, Box geometry, FootPrint geometry, ifc_type_object_id string
    -> FeatureMerger_7 [SUPPLIER]
IfcSlab (reader IFC_1)
    attributes: GlobalId char(22), Name string, Description string, ObjectType string, Tag varchar(255), PredefinedType enumeration, Annotation geometry, Axis geometry, Body geometry, Box geometry, FootPrint geometry, ifc_type_object_id string
    -> FeatureMerger_7 [SUPPLIER]
IfcBuilding (reader IFC_1)
    attributes: GlobalId char(22), Name string, Description string, ObjectType string, LongName string, CompositionType string, ElevationOfRefHeight real, ElevationOfTerrain real, BuildingAddress.Purpose enumeration, BuildingAddress.Description string, BuildingAddress.UserDefinedPurpose varchar(255), BuildingAddress.InternalLocation varchar(255), BuildingAddress.AddressLines string, BuildingAddress.PostalBox varchar(255), BuildingAddress.Town varchar(255), BuildingAddress.Region varchar(255), BuildingAddress.PostalCode varchar(255), BuildingAddress.Country varchar(255), Annotation geometry, Axis geometry, Body geometry, Box geometry, FootPrint geometry, ifc_type_object_id string
    -> AttributeRenamer
IfcSpace (reader IFC_1)
    attributes: GlobalId char(22), Name string, Description string, ObjectType string, LongName varchar(255), CompositionType enumeration, PredefinedType enumeration, ElevationWithFlooring real, Annotation geometry, Axis geometry, Body geometry, Box geometry, FootPrint geometry, ifc_type_object_id string
    -> FeatureMerger_17 [SUPPLIER]
IfcBuildingStorey (reader IFC_1)
    attributes: GlobalId char(22), Name string, Description string, ObjectType string, LongName varchar(255), CompositionType enumeration, Elevation real, Annotation geometry, Axis geometry, Body geometry, Box geometry, FootPrint geometry, ifc_type_object_id string
    -> AttributeRenamer_5

Bookmark: CityModel
AttributeRenamer_8
    ATTR_TABLE:
      RENAME_SET_DEFAULT Name > gml_name{0}
      RENAME_SET_DEFAULT Description > gml_description
    -> AttributeCreator_9
AttributeCreator_9
    ATTR_TABLE = SET_TO gml_id = id_@UUID()
    -> AttributeRenamer_9
    -> CityModel (writer GML_1)
AttributeRenamer_9
    ATTR_TABLE = RENAME_SET_DEFAULT gml_id > gml_parent_id
    -> FeatureMerger_8 [SUPPLIER]

Bookmark: GML Writer
CityModel (writer GML_1)
    attributes: adeOfAbstractFeature{} xml_xml, adeOfAbstractFeatureWithLifespan{} xml_xml, adeOfCityModel{} xml_xml, appearanceMember{}.gml_remoteSchema xml_buffer, appearanceMember{}.nilReason xml_buffer, appearanceMember{}.owns xml_boolean, appearanceMember{}.xlink_href xml_buffer, appearanceMember{}.xlink_title xml_buffer, cityObjectMember{}.gml_remoteSchema xml_buffer, cityObjectMember{}.nilReason xml_buffer, cityObjectMember{}.owns xml_boolean, cityObjectMember{}.xlink_href xml_buffer, cityObjectMember{}.xlink_title xml_buffer, creationDate xml_datetime, engineeringCRS xml_xml, engineeringCRS.gml_remoteSchema xml_buffer, engineeringCRS.nilReason xml_buffer, engineeringCRS.owns xml_boolean, engineeringCRS.xlink_href xml_buffer, engineeringCRS.xlink_title xml_buffer, featureMember{}.gml_remoteSchema xml_buffer, featureMember{}.nilReason xml_buffer, featureMember{}.owns xml_boolean, featureMember{}.xlink_href xml_buffer, featureMember{}.xlink_title xml_buffer, gml_boundedBy xml_geometry, gml_description xml_buffer, gml_description.gml_remoteSchema xml_buffer, gml_description.nilReason xml_buffer, gml_description.xlink_href xml_buffer,
      gml_description.xlink_title xml_buffer, gml_descriptionReference.gml_remoteSchema xml_buffer, gml_descriptionReference.nilReason xml_buffer, gml_descriptionReference.owns xml_boolean, gml_descriptionReference.xlink_href xml_buffer, gml_descriptionReference.xlink_title xml_buffer, gml_identifier xml_buffer, gml_identifier.codeSpace xml_buffer, gml_location xml_geometry, gml_metaDataProperty{}.about xml_buffer, gml_metaDataProperty{}.gml_GenericMetaData xml_xml, gml_metaDataProperty{}.gml_GenericMetaData.gml_id xml_buffer, gml_metaDataProperty{}.gml_remoteSchema xml_buffer, gml_metaDataProperty{}.nilReason xml_buffer, gml_metaDataProperty{}.xlink_href xml_buffer, gml_metaDataProperty{}.xlink_title xml_buffer, gml_name{} xml_buffer, gml_name{}.codeSpace xml_buffer, gml_priorityLocation xml_geometry, terminationDate xml_datetime, validFrom xml_datetime, validTo xml_datetime, versionMember{}.gml_remoteSchema xml_buffer, versionMember{}.nilReason xml_buffer, versionMember{}.owns xml_boolean, versionMember{}.xlink_href xml_buffer, versionMember{}.xlink_title xml_buffer, versionTransitionMember{}.gml_remoteSchema xml_buffer, versionTransitionMember{}.nilReason xml_buffer, versionTransitionMember{}.owns xml_boolean,
      versionTransitionMember{}.xlink_href xml_buffer, versionTransitionMember{}.xlink_title xml_buffer
Building (writer GML_1)
    attributes: creationDate xml_datetime, terminationDate xml_datetime, validFrom xml_datetime, validTo xml_datetime, generalizesTo{}.owns xml_boolean, generalizesTo{}.nilReason xml_buffer, generalizesTo{}.gml_remoteSchema xml_buffer, generalizesTo{}.xlink_href xml_buffer, generalizesTo{}.xlink_title xml_buffer, relativeToTerrain xml_char(33), relativeToWater xml_char(38), relatedTo{}.owns xml_boolean, relatedTo{}.nilReason xml_buffer, relatedTo{}.gml_remoteSchema xml_buffer, relatedTo{}.xlink_href xml_buffer, relatedTo{}.xlink_title xml_buffer, appearance{}.nilReason xml_buffer, appearance{}.gml_remoteSchema xml_buffer, appearance{}.xlink_href xml_buffer, appearance{}.xlink_title xml_buffer, appearance{}.owns xml_boolean, dynamizer{}.nilReason xml_buffer, dynamizer{}.gml_remoteSchema xml_buffer, dynamizer{}.xlink_href xml_buffer, dynamizer{}.xlink_title xml_buffer, dynamizer{}.owns xml_boolean, spaceType xml_char(8), lod0Point xml_geometry, lod0MultiSurface xml_geometry, lod1Solid xml_geometry,
      lod2Solid xml_geometry, lod2MultiSurface xml_geometry, lod2MultiCurve xml_geometry, boundary{}.nilReason xml_buffer, boundary{}.gml_remoteSchema xml_buffer, boundary{}.xlink_href xml_buffer, boundary{}.xlink_title xml_buffer, boundary{}.owns xml_boolean, lod3Solid xml_geometry, lod3MultiSurface xml_geometry, lod3MultiCurve xml_geometry, lod1TerrainIntersectionCurve xml_geometry, lod2TerrainIntersectionCurve xml_geometry, lod3TerrainIntersectionCurve xml_geometry, pointCloud.nilReason xml_buffer, pointCloud.gml_remoteSchema xml_buffer, pointCloud.xlink_href xml_buffer, pointCloud.xlink_title xml_buffer, pointCloud.owns xml_boolean, lod1ImplicitRepresentation.nilReason xml_buffer, lod1ImplicitRepresentation.gml_remoteSchema xml_buffer, lod1ImplicitRepresentation.xlink_href xml_buffer, lod1ImplicitRepresentation.xlink_title xml_buffer, lod1ImplicitRepresentation.owns xml_boolean, lod2ImplicitRepresentation.nilReason xml_buffer, lod2ImplicitRepresentation.gml_remoteSchema xml_buffer, lod2ImplicitRepresentation.xlink_href xml_buffer, lod2ImplicitRepresentation.xlink_title xml_buffer, lod2ImplicitRepresentation.owns xml_boolean, lod3ImplicitRepresentation.nilReason xml_buffer,
      lod3ImplicitRepresentation.gml_remoteSchema xml_buffer, lod3ImplicitRepresentation.xlink_href xml_buffer, lod3ImplicitRepresentation.xlink_title xml_buffer, lod3ImplicitRepresentation.owns xml_boolean, conditionOfConstruction xml_char(17), dateOfConstruction xml_date, dateOfDemolition xml_date, class xml_buffer, class.codeSpace xml_buffer, function{} xml_buffer, function{}.codeSpace xml_buffer, usage{} xml_buffer, usage{}.codeSpace xml_buffer, roofType xml_buffer, roofType.codeSpace xml_buffer, storeysAboveGround xml_int64, storeysBelowGround xml_int64, storeyHeightsAboveGround xml_buffer, storeyHeightsAboveGround.uom xml_buffer, storeyHeightsBelowGround xml_buffer, storeyHeightsBelowGround.uom xml_buffer, buildingConstructiveElement{}.owns xml_boolean, buildingInstallation{}.owns xml_boolean, buildingFurniture{}.owns xml_boolean, buildingSubdivision{}.owns xml_boolean, address{}.nilReason xml_buffer, address{}.gml_remoteSchema xml_buffer, address{}.xlink_href xml_buffer, address{}.xlink_title xml_buffer, address{}.owns xml_boolean,
      buildingPart{}.nilReason xml_buffer, buildingPart{}.gml_remoteSchema xml_buffer, buildingPart{}.xlink_href xml_buffer, buildingPart{}.xlink_title xml_buffer, buildingPart{}.owns xml_boolean, gml_metaDataProperty{}.about xml_buffer, gml_metaDataProperty{}.nilReason xml_buffer, gml_metaDataProperty{}.gml_remoteSchema xml_buffer, gml_metaDataProperty{}.xlink_href xml_buffer, gml_metaDataProperty{}.xlink_title xml_buffer, gml_description xml_buffer, gml_description.nilReason xml_buffer, gml_description.gml_remoteSchema xml_buffer, gml_description.xlink_href xml_buffer, gml_description.xlink_title xml_buffer, gml_descriptionReference.owns xml_boolean, gml_descriptionReference.nilReason xml_buffer, gml_descriptionReference.gml_remoteSchema xml_buffer, gml_descriptionReference.xlink_href xml_buffer, gml_descriptionReference.xlink_title xml_buffer, gml_identifier xml_buffer, gml_identifier.codeSpace xml_buffer, gml_name{} xml_buffer, gml_name{}.codeSpace xml_buffer, gml_boundedBy xml_geometry, gml_location xml_geometry, buildingRoom{}.owns xml_boolean, gml_metaDataProperty{}.gml_GenericMetaData xml_xml, gml_metaDataProperty{}.gml_GenericMetaData.gml_id xml_buffer, gml_priorityLocation xml_geometry,
      externalReference{}.ExternalReference.targetResource xml_buffer, externalReference{}.ExternalReference.informationSystem xml_buffer, externalReference{}.ExternalReference.relationType xml_buffer, relatedTo{}.CityObjectRelation.gml_id xml_buffer, relatedTo{}.CityObjectRelation.gml_metaDataProperty{}.about xml_buffer, relatedTo{}.CityObjectRelation.gml_metaDataProperty{}.nilReason xml_buffer, relatedTo{}.CityObjectRelation.gml_metaDataProperty{}.gml_remoteSchema xml_buffer, relatedTo{}.CityObjectRelation.gml_metaDataProperty{}.xlink_href xml_buffer, relatedTo{}.CityObjectRelation.gml_metaDataProperty{}.xlink_title xml_buffer, relatedTo{}.CityObjectRelation.gml_metaDataProperty{}.gml_GenericMetaData xml_xml, relatedTo{}.CityObjectRelation.gml_metaDataProperty{}.gml_GenericMetaData.gml_id xml_buffer, relatedTo{}.CityObjectRelation.gml_description xml_buffer, relatedTo{}.CityObjectRelation.gml_description.nilReason xml_buffer, relatedTo{}.CityObjectRelation.gml_description.gml_remoteSchema xml_buffer, relatedTo{}.CityObjectRelation.gml_description.xlink_href xml_buffer, relatedTo{}.CityObjectRelation.gml_description.xlink_title xml_buffer, relatedTo{}.CityObjectRelation.gml_descriptionReference.owns xml_boolean, relatedTo{}.CityObjectRelation.gml_descriptionReference.nilReason xml_buffer, relatedTo{}.CityObjectRelation.gml_descriptionReference.gml_remoteSchema xml_buffer, relatedTo{}.CityObjectRelation.gml_descriptionReference.xlink_href xml_buffer, relatedTo{}.CityObjectRelation.gml_descriptionReference.xlink_title xml_buffer, relatedTo{}.CityObjectRelation.gml_identifier xml_buffer, relatedTo{}.CityObjectRelation.gml_identifier.codeSpace xml_buffer, relatedTo{}.CityObjectRelation.gml_name{} xml_buffer, relatedTo{}.CityObjectRelation.gml_name{}.codeSpace xml_buffer, relatedTo{}.CityObjectRelation.relatedTo.nilReason xml_buffer, relatedTo{}.CityObjectRelation.relatedTo.gml_remoteSchema xml_buffer, relatedTo{}.CityObjectRelation.relatedTo.xlink_href xml_buffer, relatedTo{}.CityObjectRelation.relatedTo.xlink_title xml_buffer, relatedTo{}.CityObjectRelation.relatedTo.owns xml_boolean,
      genericAttribute{}.DateAttribute.name xml_buffer, genericAttribute{}.DateAttribute.value xml_date, genericAttribute{}.DoubleAttribute.name xml_buffer, genericAttribute{}.DoubleAttribute.value xml_real64, genericAttribute{}.GenericAttributeSet.name xml_buffer, genericAttribute{}.GenericAttributeSet.codeSpace xml_buffer, genericAttribute{}.GenericAttributeSet.genericAttribute{}.DateAttribute xml_xml, genericAttribute{}.GenericAttributeSet.genericAttribute{}.DoubleAttribute xml_xml, genericAttribute{}.GenericAttributeSet.genericAttribute{}.GenericAttributeSet xml_xml, genericAttribute{}.GenericAttributeSet.genericAttribute{}.IntAttribute xml_xml, genericAttribute{}.GenericAttributeSet.genericAttribute{}.MeasureAttribute xml_xml, genericAttribute{}.GenericAttributeSet.genericAttribute{}.StringAttribute xml_xml, genericAttribute{}.GenericAttributeSet.genericAttribute{}.UriAttribute xml_xml, genericAttribute{}.IntAttribute.name xml_buffer, genericAttribute{}.IntAttribute.value xml_int64, genericAttribute{}.MeasureAttribute.name xml_buffer, genericAttribute{}.MeasureAttribute.value xml_real64, genericAttribute{}.MeasureAttribute.value.uom xml_buffer, genericAttribute{}.StringAttribute.name xml_buffer, genericAttribute{}.StringAttribute.value xml_buffer, genericAttribute{}.UriAttribute.name xml_buffer, genericAttribute{}.UriAttribute.value xml_buffer, volume{}.QualifiedVolume.volume xml_real64, volume{}.QualifiedVolume.volume.uom xml_buffer, area{}.QualifiedArea.area xml_real64, area{}.QualifiedArea.area.uom xml_buffer, occupancy{}.Occupancy.numberOfOccupants xml_int64, constructionEvent{}.ConstructionEvent.dateOfEvent xml_date, constructionEvent{}.ConstructionEvent.description xml_buffer, elevation{}.Elevation.elevationReference xml_buffer,
      elevation{}.Elevation.elevationValue xml_buffer, elevation{}.Elevation.elevationValue.srsName xml_buffer, elevation{}.Elevation.elevationValue.srsDimension xml_uint64, elevation{}.Elevation.elevationValue.axisLabels xml_buffer, elevation{}.Elevation.elevationValue.uomLabels xml_buffer, height{}.Height.highReference xml_buffer, height{}.Height.lowReference xml_buffer, height{}.Height.status xml_char(9), height{}.Height.value xml_real64, height{}.Height.value.uom xml_buffer, adeOfAbstractFeature{} xml_xml, adeOfAbstractFeatureWithLifespan{} xml_xml, relatedTo{}.CityObjectRelation.genericAttribute{}.CodeAttribute.name xml_buffer, relatedTo{}.CityObjectRelation.genericAttribute{}.CodeAttribute.value xml_buffer, relatedTo{}.CityObjectRelation.genericAttribute{}.CodeAttribute.value.codeSpace xml_buffer, relatedTo{}.CityObjectRelation.genericAttribute{}.DateAttribute.name xml_buffer, relatedTo{}.CityObjectRelation.genericAttribute{}.DateAttribute.value xml_date, relatedTo{}.CityObjectRelation.genericAttribute{}.DoubleAttribute.name xml_buffer, relatedTo{}.CityObjectRelation.genericAttribute{}.DoubleAttribute.value xml_real64, relatedTo{}.CityObjectRelation.genericAttribute{}.GenericAttributeSet.name xml_buffer, relatedTo{}.CityObjectRelation.genericAttribute{}.GenericAttributeSet.codeSpace xml_buffer, relatedTo{}.CityObjectRelation.genericAttribute{}.GenericAttributeSet.genericAttribute{}.CodeAttribute xml_xml, relatedTo{}.CityObjectRelation.genericAttribute{}.GenericAttributeSet.genericAttribute{}.DateAttribute xml_xml, relatedTo{}.CityObjectRelation.genericAttribute{}.GenericAttributeSet.genericAttribute{}.DoubleAttribute xml_xml, relatedTo{}.CityObjectRelation.genericAttribute{}.GenericAttributeSet.genericAttribute{}.GenericAttributeSet xml_xml, relatedTo{}.CityObjectRelation.genericAttribute{}.GenericAttributeSet.genericAttribute{}.IntAttribute xml_xml, relatedTo{}.CityObjectRelation.genericAttribute{}.GenericAttributeSet.genericAttribute{}.MeasureAttribute xml_xml, relatedTo{}.CityObjectRelation.genericAttribute{}.GenericAttributeSet.genericAttribute{}.StringAttribute xml_xml, relatedTo{}.CityObjectRelation.genericAttribute{}.GenericAttributeSet.genericAttribute{}.UriAttribute xml_xml, relatedTo{}.CityObjectRelation.genericAttribute{}.IntAttribute.name xml_buffer,
      relatedTo{}.CityObjectRelation.genericAttribute{}.IntAttribute.value xml_int64, relatedTo{}.CityObjectRelation.genericAttribute{}.MeasureAttribute.name xml_buffer, relatedTo{}.CityObjectRelation.genericAttribute{}.MeasureAttribute.value xml_real64, relatedTo{}.CityObjectRelation.genericAttribute{}.MeasureAttribute.value.uom xml_buffer, relatedTo{}.CityObjectRelation.genericAttribute{}.StringAttribute.name xml_buffer, relatedTo{}.CityObjectRelation.genericAttribute{}.StringAttribute.value xml_buffer, relatedTo{}.CityObjectRelation.genericAttribute{}.UriAttribute.name xml_buffer, relatedTo{}.CityObjectRelation.genericAttribute{}.UriAttribute.value xml_buffer, relatedTo{}.CityObjectRelation.relationType xml_buffer, relatedTo{}.CityObjectRelation.relationType.codeSpace xml_buffer, genericAttribute{}.CodeAttribute.name xml_buffer, genericAttribute{}.CodeAttribute.value xml_buffer, genericAttribute{}.CodeAttribute.value.codeSpace xml_buffer, genericAttribute{}.GenericAttributeSet.genericAttribute{}.CodeAttribute xml_xml, adeOfAbstractCityObject{} xml_xml, volume{}.QualifiedVolume.typeOfVolume xml_buffer, volume{}.QualifiedVolume.typeOfVolume.codeSpace xml_buffer, area{}.QualifiedArea.typeOfArea xml_buffer, area{}.QualifiedArea.typeOfArea.codeSpace xml_buffer, lod0MultiCurve xml_geometry, adeOfAbstractSpace{} xml_xml, adeOfAbstractPhysicalSpace{} xml_xml, lod1ImplicitRepresentation.ImplicitGeometry.gml_id xml_buffer, lod1ImplicitRepresentation.ImplicitGeometry.gml_metaDataProperty{}.about xml_buffer, lod1ImplicitRepresentation.ImplicitGeometry.gml_metaDataProperty{}.nilReason xml_buffer, lod1ImplicitRepresentation.ImplicitGeometry.gml_metaDataProperty{}.gml_remoteSchema xml_buffer, lod1ImplicitRepresentation.ImplicitGeometry.gml_metaDataProperty{}.xlink_href xml_buffer, lod1ImplicitRepresentation.ImplicitGeometry.gml_metaDataProperty{}.xlink_title xml_buffer, lod1ImplicitRepresentation.ImplicitGeometry.gml_metaDataProperty{}.gml_GenericMetaData xml_xml, lod1ImplicitRepresentation.ImplicitGeometry.gml_metaDataProperty{}.gml_GenericMetaData.gml_id xml_buffer,
      lod1ImplicitRepresentation.ImplicitGeometry.gml_description xml_buffer, lod1ImplicitRepresentation.ImplicitGeometry.gml_description.nilReason xml_buffer, lod1ImplicitRepresentation.ImplicitGeometry.gml_description.gml_remoteSchema xml_buffer, lod1ImplicitRepresentation.ImplicitGeometry.gml_description.xlink_href xml_buffer, lod1ImplicitRepresentation.ImplicitGeometry.gml_description.xlink_title xml_buffer, lod1ImplicitRepresentation.ImplicitGeometry.gml_descriptionReference.owns xml_boolean, lod1ImplicitRepresentation.ImplicitGeometry.gml_descriptionReference.nilReason xml_buffer, lod1ImplicitRepresentation.ImplicitGeometry.gml_descriptionReference.gml_remoteSchema xml_buffer, lod1ImplicitRepresentation.ImplicitGeometry.gml_descriptionReference.xlink_href xml_buffer, lod1ImplicitRepresentation.ImplicitGeometry.gml_descriptionReference.xlink_title xml_buffer, lod1ImplicitRepresentation.ImplicitGeometry.gml_identifier xml_buffer, lod1ImplicitRepresentation.ImplicitGeometry.gml_identifier.codeSpace xml_buffer, lod1ImplicitRepresentation.ImplicitGeometry.gml_name{} xml_buffer, lod1ImplicitRepresentation.ImplicitGeometry.gml_name{}.codeSpace xml_buffer, lod1ImplicitRepresentation.ImplicitGeometry.transformationMatrix xml_buffer, lod1ImplicitRepresentation.ImplicitGeometry.mimeType xml_buffer, lod1ImplicitRepresentation.ImplicitGeometry.mimeType.codeSpace xml_buffer, lod1ImplicitRepresentation.ImplicitGeometry.libraryObject xml_buffer, lod1ImplicitRepresentation.ImplicitGeometry.referencePoint xml_geometry, lod1ImplicitRepresentation.ImplicitGeometry.relativeGeometry xml_geometry, lod1ImplicitRepresentation.ImplicitGeometry.appearance{}.nilReason xml_buffer, lod1ImplicitRepresentation.ImplicitGeometry.appearance{}.gml_remoteSchema xml_buffer, lod1ImplicitRepresentation.ImplicitGeometry.appearance{}.xlink_href xml_buffer, lod1ImplicitRepresentation.ImplicitGeometry.appearance{}.xlink_title xml_buffer, lod1ImplicitRepresentation.ImplicitGeometry.appearance{}.owns xml_boolean, lod2ImplicitRepresentation.ImplicitGeometry.gml_id xml_buffer, lod2ImplicitRepresentation.ImplicitGeometry.gml_metaDataProperty{}.about xml_buffer, lod2ImplicitRepresentation.ImplicitGeometry.gml_metaDataProperty{}.nilReason xml_buffer, lod2ImplicitRepresentation.ImplicitGeometry.gml_metaDataProperty{}.gml_remoteSchema xml_buffer, lod2ImplicitRepresentation.ImplicitGeometry.gml_metaDataProperty{}.xlink_href xml_buffer,
      lod2ImplicitRepresentation.ImplicitGeometry.gml_metaDataProperty{}.xlink_title xml_buffer, lod2ImplicitRepresentation.ImplicitGeometry.gml_metaDataProperty{}.gml_GenericMetaData xml_xml, lod2ImplicitRepresentation.ImplicitGeometry.gml_metaDataProperty{}.gml_GenericMetaData.gml_id xml_buffer, lod2ImplicitRepresentation.ImplicitGeometry.gml_description xml_buffer, lod2ImplicitRepresentation.ImplicitGeometry.gml_description.nilReason xml_buffer, lod2ImplicitRepresentation.ImplicitGeometry.gml_description.gml_remoteSchema xml_buffer, lod2ImplicitRepresentation.ImplicitGeometry.gml_description.xlink_href xml_buffer, lod2ImplicitRepresentation.ImplicitGeometry.gml_description.xlink_title xml_buffer, lod2ImplicitRepresentation.ImplicitGeometry.gml_descriptionReference.owns xml_boolean, lod2ImplicitRepresentation.ImplicitGeometry.gml_descriptionReference.nilReason xml_buffer, lod2ImplicitRepresentation.ImplicitGeometry.gml_descriptionReference.gml_remoteSchema xml_buffer, lod2ImplicitRepresentation.ImplicitGeometry.gml_descriptionReference.xlink_href xml_buffer, lod2ImplicitRepresentation.ImplicitGeometry.gml_descriptionReference.xlink_title xml_buffer, lod2ImplicitRepresentation.ImplicitGeometry.gml_identifier xml_buffer, lod2ImplicitRepresentation.ImplicitGeometry.gml_identifier.codeSpace xml_buffer, lod2ImplicitRepresentation.ImplicitGeometry.gml_name{} xml_buffer, lod2ImplicitRepresentation.ImplicitGeometry.gml_name{}.codeSpace xml_buffer, lod2ImplicitRepresentation.ImplicitGeometry.transformationMatrix xml_buffer, lod2ImplicitRepresentation.ImplicitGeometry.mimeType xml_buffer, lod2ImplicitRepresentation.ImplicitGeometry.mimeType.codeSpace xml_buffer, lod2ImplicitRepresentation.ImplicitGeometry.libraryObject xml_buffer, lod2ImplicitRepresentation.ImplicitGeometry.referencePoint xml_geometry, lod2ImplicitRepresentation.ImplicitGeometry.relativeGeometry xml_geometry, lod2ImplicitRepresentation.ImplicitGeometry.appearance{}.nilReason xml_buffer, lod2ImplicitRepresentation.ImplicitGeometry.appearance{}.gml_remoteSchema xml_buffer, lod2ImplicitRepresentation.ImplicitGeometry.appearance{}.xlink_href xml_buffer, lod2ImplicitRepresentation.ImplicitGeometry.appearance{}.xlink_title xml_buffer, lod2ImplicitRepresentation.ImplicitGeometry.appearance{}.owns xml_boolean, lod3ImplicitRepresentation.ImplicitGeometry.gml_id xml_buffer, lod3ImplicitRepresentation.ImplicitGeometry.gml_metaDataProperty{}.about xml_buffer,
      lod3ImplicitRepresentation.ImplicitGeometry.gml_metaDataProperty{}.nilReason xml_buffer, lod3ImplicitRepresentation.ImplicitGeometry.gml_metaDataProperty{}.gml_remoteSchema xml_buffer, lod3ImplicitRepresentation.ImplicitGeometry.gml_metaDataProperty{}.xlink_href xml_buffer, lod3ImplicitRepresentation.ImplicitGeometry.gml_metaDataProperty{}.xlink_title xml_buffer, lod3ImplicitRepresentation.ImplicitGeometry.gml_metaDataProperty{}.gml_GenericMetaData xml_xml, lod3ImplicitRepresentation.ImplicitGeometry.gml_metaDataProperty{}.gml_GenericMetaData.gml_id xml_buffer, lod3ImplicitRepresentation.ImplicitGeometry.gml_description xml_buffer, lod3ImplicitRepresentation.ImplicitGeometry.gml_description.nilReason xml_buffer, lod3ImplicitRepresentation.ImplicitGeometry.gml_description.gml_remoteSchema xml_buffer, lod3ImplicitRepresentation.ImplicitGeometry.gml_description.xlink_href xml_buffer, lod3ImplicitRepresentation.ImplicitGeometry.gml_description.xlink_title xml_buffer, lod3ImplicitRepresentation.ImplicitGeometry.gml_descriptionReference.owns xml_boolean, lod3ImplicitRepresentation.ImplicitGeometry.gml_descriptionReference.nilReason xml_buffer, lod3ImplicitRepresentation.ImplicitGeometry.gml_descriptionReference.gml_remoteSchema xml_buffer, lod3ImplicitRepresentation.ImplicitGeometry.gml_descriptionReference.xlink_href xml_buffer, lod3ImplicitRepresentation.ImplicitGeometry.gml_descriptionReference.xlink_title xml_buffer, lod3ImplicitRepresentation.ImplicitGeometry.gml_identifier xml_buffer, lod3ImplicitRepresentation.ImplicitGeometry.gml_identifier.codeSpace xml_buffer, lod3ImplicitRepresentation.ImplicitGeometry.gml_name{} xml_buffer, lod3ImplicitRepresentation.ImplicitGeometry.gml_name{}.codeSpace xml_buffer, lod3ImplicitRepresentation.ImplicitGeometry.transformationMatrix xml_buffer, lod3ImplicitRepresentation.ImplicitGeometry.mimeType xml_buffer, lod3ImplicitRepresentation.ImplicitGeometry.mimeType.codeSpace xml_buffer, lod3ImplicitRepresentation.ImplicitGeometry.libraryObject xml_buffer, lod3ImplicitRepresentation.ImplicitGeometry.referencePoint xml_geometry, lod3ImplicitRepresentation.ImplicitGeometry.relativeGeometry xml_geometry, lod3ImplicitRepresentation.ImplicitGeometry.appearance{}.nilReason xml_buffer, lod3ImplicitRepresentation.ImplicitGeometry.appearance{}.gml_remoteSchema xml_buffer, lod3ImplicitRepresentation.ImplicitGeometry.appearance{}.xlink_href xml_buffer, lod3ImplicitRepresentation.ImplicitGeometry.appearance{}.xlink_title xml_buffer,
      lod3ImplicitRepresentation.ImplicitGeometry.appearance{}.owns xml_boolean, adeOfAbstractOccupiedSpace{} xml_xml, constructionEvent{}.ConstructionEvent.event xml_buffer, constructionEvent{}.ConstructionEvent.event.codeSpace xml_buffer, elevation{}.Elevation.elevationReference.codeSpace xml_buffer, height{}.Height.highReference.codeSpace xml_buffer, height{}.Height.lowReference.codeSpace xml_buffer, occupancy{}.Occupancy.interval xml_buffer, occupancy{}.Occupancy.interval.codeSpace xml_buffer, occupancy{}.Occupancy.occupantType xml_buffer, occupancy{}.Occupancy.occupantType.codeSpace xml_buffer, adeOfAbstractConstruction{} xml_xml, adeOfAbstractBuilding{} xml_xml, adeOfBuilding{} xml_xml
BuildingInstallation (writer GML_1)
    attributes: appearance{}.gml_remoteSchema xml_buffer, appearance{}.nilReason xml_buffer, appearance{}.owns xml_boolean, appearance{}.xlink_href xml_buffer, appearance{}.xlink_title xml_buffer, boundary{}.gml_remoteSchema xml_buffer, boundary{}.nilReason xml_buffer, boundary{}.owns xml_boolean, boundary{}.xlink_href xml_buffer, boundary{}.xlink_title xml_buffer, class xml_buffer, class.codeSpace xml_buffer, creationDate xml_datetime, dynamizer{}.gml_remoteSchema xml_buffer, dynamizer{}.nilReason xml_buffer, dynamizer{}.owns xml_boolean, dynamizer{}.xlink_href xml_buffer, dynamizer{}.xlink_title xml_buffer, function{} xml_buffer, function{}.codeSpace xml_buffer, generalizesTo{}.gml_remoteSchema xml_buffer, generalizesTo{}.nilReason xml_buffer, generalizesTo{}.owns xml_boolean, generalizesTo{}.xlink_href xml_buffer, generalizesTo{}.xlink_title xml_buffer, gml_boundedBy xml_geometry, gml_description xml_buffer, gml_description.gml_remoteSchema xml_buffer, gml_description.nilReason xml_buffer, gml_description.xlink_href xml_buffer,
      gml_description.xlink_title xml_buffer, gml_descriptionReference.gml_remoteSchema xml_buffer, gml_descriptionReference.nilReason xml_buffer, gml_descriptionReference.owns xml_boolean, gml_descriptionReference.xlink_href xml_buffer, gml_descriptionReference.xlink_title xml_buffer, gml_identifier xml_buffer, gml_identifier.codeSpace xml_buffer, gml_location xml_geometry, gml_metaDataProperty{}.about xml_buffer, gml_metaDataProperty{}.gml_remoteSchema xml_buffer, gml_metaDataProperty{}.nilReason xml_buffer, gml_metaDataProperty{}.xlink_href xml_buffer, gml_metaDataProperty{}.xlink_title xml_buffer, gml_name{} xml_buffer, gml_name{}.codeSpace xml_buffer, lod0MultiSurface xml_geometry, lod0Point xml_geometry, lod1ImplicitRepresentation.gml_remoteSchema xml_buffer, lod1ImplicitRepresentation.nilReason xml_buffer, lod1ImplicitRepresentation.owns xml_boolean, lod1ImplicitRepresentation.xlink_href xml_buffer, lod1ImplicitRepresentation.xlink_title xml_buffer, lod1Solid xml_geometry, lod1TerrainIntersectionCurve xml_geometry, lod2ImplicitRepresentation.gml_remoteSchema xml_buffer, lod2ImplicitRepresentation.nilReason xml_buffer, lod2ImplicitRepresentation.owns xml_boolean, lod2ImplicitRepresentation.xlink_href xml_buffer, lod2ImplicitRepresentation.xlink_title xml_buffer,
      lod2MultiCurve xml_geometry, lod2MultiSurface xml_geometry, lod2Solid xml_geometry, lod2TerrainIntersectionCurve xml_geometry, lod3ImplicitRepresentation.gml_remoteSchema xml_buffer, lod3ImplicitRepresentation.nilReason xml_buffer, lod3ImplicitRepresentation.owns xml_boolean, lod3ImplicitRepresentation.xlink_href xml_buffer, lod3ImplicitRepresentation.xlink_title xml_buffer, lod3MultiCurve xml_geometry, lod3MultiSurface xml_geometry, lod3Solid xml_geometry, lod3TerrainIntersectionCurve xml_geometry, pointCloud.gml_remoteSchema xml_buffer, pointCloud.nilReason xml_buffer, pointCloud.owns xml_boolean, pointCloud.xlink_href xml_buffer, pointCloud.xlink_title xml_buffer, relatedTo{}.gml_remoteSchema xml_buffer, relatedTo{}.nilReason xml_buffer, relatedTo{}.owns xml_boolean, relatedTo{}.xlink_href xml_buffer, relatedTo{}.xlink_title xml_buffer, relationToConstruction xml_char(20), relativeToTerrain xml_char(33), relativeToWater xml_char(38), spaceType xml_char(8), terminationDate xml_datetime, usage{} xml_buffer, usage{}.codeSpace xml_buffer,
      validFrom xml_datetime, validTo xml_datetime, gml_metaDataProperty{}.gml_GenericMetaData xml_xml, gml_metaDataProperty{}.gml_GenericMetaData.gml_id xml_buffer, gml_priorityLocation xml_geometry, externalReference{}.ExternalReference.targetResource xml_buffer, externalReference{}.ExternalReference.informationSystem xml_buffer, externalReference{}.ExternalReference.relationType xml_buffer, relatedTo{}.CityObjectRelation.gml_id xml_buffer, relatedTo{}.CityObjectRelation.gml_metaDataProperty{}.about xml_buffer, relatedTo{}.CityObjectRelation.gml_metaDataProperty{}.nilReason xml_buffer, relatedTo{}.CityObjectRelation.gml_metaDataProperty{}.gml_remoteSchema xml_buffer, relatedTo{}.CityObjectRelation.gml_metaDataProperty{}.xlink_href xml_buffer, relatedTo{}.CityObjectRelation.gml_metaDataProperty{}.xlink_title xml_buffer, relatedTo{}.CityObjectRelation.gml_metaDataProperty{}.gml_GenericMetaData xml_xml, relatedTo{}.CityObjectRelation.gml_metaDataProperty{}.gml_GenericMetaData.gml_id xml_buffer, relatedTo{}.CityObjectRelation.gml_description xml_buffer, relatedTo{}.CityObjectRelation.gml_description.nilReason xml_buffer, relatedTo{}.CityObjectRelation.gml_description.gml_remoteSchema xml_buffer, relatedTo{}.CityObjectRelation.gml_description.xlink_href xml_buffer, relatedTo{}.CityObjectRelation.gml_description.xlink_title xml_buffer, relatedTo{}.CityObjectRelation.gml_descriptionReference.owns xml_boolean, relatedTo{}.CityObjectRelation.gml_descriptionReference.nilReason xml_buffer, relatedTo{}.CityObjectRelation.gml_descriptionReference.gml_remoteSchema xml_buffer, relatedTo{}.CityObjectRelation.gml_descriptionReference.xlink_href xml_buffer, relatedTo{}.CityObjectRelation.gml_descriptionReference.xlink_title xml_buffer, relatedTo{}.CityObjectRelation.gml_identifier xml_buffer, relatedTo{}.CityObjectRelation.gml_identifier.codeSpace xml_buffer, relatedTo{}.CityObjectRelation.gml_name{} xml_buffer, relatedTo{}.CityObjectRelation.gml_name{}.codeSpace xml_buffer,
      relatedTo{}.CityObjectRelation.relatedTo.nilReason xml_buffer, relatedTo{}.CityObjectRelation.relatedTo.gml_remoteSchema xml_buffer, relatedTo{}.CityObjectRelation.relatedTo.xlink_href xml_buffer, relatedTo{}.CityObjectRelation.relatedTo.xlink_title xml_buffer, relatedTo{}.CityObjectRelation.relatedTo.owns xml_boolean, genericAttribute{}.DateAttribute.name xml_buffer, genericAttribute{}.DateAttribute.value xml_date, genericAttribute{}.DoubleAttribute.name xml_buffer, genericAttribute{}.DoubleAttribute.value xml_real64, genericAttribute{}.GenericAttributeSet.name xml_buffer, genericAttribute{}.GenericAttributeSet.codeSpace xml_buffer, genericAttribute{}.GenericAttributeSet.genericAttribute{}.DateAttribute xml_xml, genericAttribute{}.GenericAttributeSet.genericAttribute{}.DoubleAttribute xml_xml, genericAttribute{}.GenericAttributeSet.genericAttribute{}.GenericAttributeSet xml_xml, genericAttribute{}.GenericAttributeSet.genericAttribute{}.IntAttribute xml_xml, genericAttribute{}.GenericAttributeSet.genericAttribute{}.MeasureAttribute xml_xml, genericAttribute{}.GenericAttributeSet.genericAttribute{}.StringAttribute xml_xml, genericAttribute{}.GenericAttributeSet.genericAttribute{}.UriAttribute xml_xml, genericAttribute{}.IntAttribute.name xml_buffer, genericAttribute{}.IntAttribute.value xml_int64, genericAttribute{}.MeasureAttribute.name xml_buffer, genericAttribute{}.MeasureAttribute.value xml_real64, genericAttribute{}.MeasureAttribute.value.uom xml_buffer, genericAttribute{}.StringAttribute.name xml_buffer, genericAttribute{}.StringAttribute.value xml_buffer, genericAttribute{}.UriAttribute.name xml_buffer, genericAttribute{}.UriAttribute.value xml_buffer, volume{}.QualifiedVolume.volume xml_real64, volume{}.QualifiedVolume.volume.uom xml_buffer, area{}.QualifiedArea.area xml_real64,
      area{}.QualifiedArea.area.uom xml_buffer, adeOfAbstractFeature{} xml_xml, adeOfAbstractFeatureWithLifespan{} xml_xml, relatedTo{}.CityObjectRelation.genericAttribute{}.CodeAttribute.name xml_buffer, relatedTo{}.CityObjectRelation.genericAttribute{}.CodeAttribute.value xml_buffer, relatedTo{}.CityObjectRelation.genericAttribute{}.CodeAttribute.value.codeSpace xml_buffer, relatedTo{}.CityObjectRelation.genericAttribute{}.DateAttribute.name xml_buffer, relatedTo{}.CityObjectRelation.genericAttribute{}.DateAttribute.value xml_date, relatedTo{}.CityObjectRelation.genericAttribute{}.DoubleAttribute.name xml_buffer, relatedTo{}.CityObjectRelation.genericAttribute{}.DoubleAttribute.value xml_real64, relatedTo{}.CityObjectRelation.genericAttribute{}.GenericAttributeSet.name xml_buffer, relatedTo{}.CityObjectRelation.genericAttribute{}.GenericAttributeSet.codeSpace xml_buffer, relatedTo{}.CityObjectRelation.genericAttribute{}.GenericAttributeSet.genericAttribute{}.CodeAttribute xml_xml, relatedTo{}.CityObjectRelation.genericAttribute{}.GenericAttributeSet.genericAttribute{}.DateAttribute xml_xml, relatedTo{}.CityObjectRelation.genericAttribute{}.GenericAttributeSet.genericAttribute{}.DoubleAttribute xml_xml, relatedTo{}.CityObjectRelation.genericAttribute{}.GenericAttributeSet.genericAttribute{}.GenericAttributeSet xml_xml, relatedTo{}.CityObjectRelation.genericAttribute{}.GenericAttributeSet.genericAttribute{}.IntAttribute xml_xml, relatedTo{}.CityObjectRelation.genericAttribute{}.GenericAttributeSet.genericAttribute{}.MeasureAttribute xml_xml, relatedTo{}.CityObjectRelation.genericAttribute{}.GenericAttributeSet.genericAttribute{}.StringAttribute xml_xml, relatedTo{}.CityObjectRelation.genericAttribute{}.GenericAttributeSet.genericAttribute{}.UriAttribute xml_xml, relatedTo{}.CityObjectRelation.genericAttribute{}.IntAttribute.name xml_buffer, relatedTo{}.CityObjectRelation.genericAttribute{}.IntAttribute.value xml_int64, relatedTo{}.CityObjectRelation.genericAttribute{}.MeasureAttribute.name xml_buffer, relatedTo{}.CityObjectRelation.genericAttribute{}.MeasureAttribute.value xml_real64, relatedTo{}.CityObjectRelation.genericAttribute{}.MeasureAttribute.value.uom xml_buffer, relatedTo{}.CityObjectRelation.genericAttribute{}.StringAttribute.name xml_buffer, relatedTo{}.CityObjectRelation.genericAttribute{}.StringAttribute.value xml_buffer, relatedTo{}.CityObjectRelation.genericAttribute{}.UriAttribute.name xml_buffer, relatedTo{}.CityObjectRelation.genericAttribute{}.UriAttribute.value xml_buffer, relatedTo{}.CityObjectRelation.relationType xml_buffer,
      relatedTo{}.CityObjectRelation.relationType.codeSpace xml_buffer, genericAttribute{}.CodeAttribute.name xml_buffer, genericAttribute{}.CodeAttribute.value xml_buffer, genericAttribute{}.CodeAttribute.value.codeSpace xml_buffer, genericAttribute{}.GenericAttributeSet.genericAttribute{}.CodeAttribute xml_xml, adeOfAbstractCityObject{} xml_xml, volume{}.QualifiedVolume.typeOfVolume xml_buffer, volume{}.QualifiedVolume.typeOfVolume.codeSpace xml_buffer, area{}.QualifiedArea.typeOfArea xml_buffer, area{}.QualifiedArea.typeOfArea.codeSpace xml_buffer, lod0MultiCurve xml_geometry, adeOfAbstractSpace{} xml_xml, adeOfAbstractPhysicalSpace{} xml_xml, lod1ImplicitRepresentation.ImplicitGeometry.gml_id xml_buffer, lod1ImplicitRepresentation.ImplicitGeometry.gml_metaDataProperty{}.about xml_buffer, lod1ImplicitRepresentation.ImplicitGeometry.gml_metaDataProperty{}.nilReason xml_buffer, lod1ImplicitRepresentation.ImplicitGeometry.gml_metaDataProperty{}.gml_remoteSchema xml_buffer, lod1ImplicitRepresentation.ImplicitGeometry.gml_metaDataProperty{}.xlink_href xml_buffer, lod1ImplicitRepresentation.ImplicitGeometry.gml_metaDataProperty{}.xlink_title xml_buffer, lod1ImplicitRepresentation.ImplicitGeometry.gml_metaDataProperty{}.gml_GenericMetaData xml_xml, lod1ImplicitRepresentation.ImplicitGeometry.gml_metaDataProperty{}.gml_GenericMetaData.gml_id xml_buffer, lod1ImplicitRepresentation.ImplicitGeometry.gml_description xml_buffer, lod1ImplicitRepresentation.ImplicitGeometry.gml_description.nilReason xml_buffer, lod1ImplicitRepresentation.ImplicitGeometry.gml_description.gml_remoteSchema xml_buffer, lod1ImplicitRepresentation.ImplicitGeometry.gml_description.xlink_href xml_buffer, lod1ImplicitRepresentation.ImplicitGeometry.gml_description.xlink_title xml_buffer, lod1ImplicitRepresentation.ImplicitGeometry.gml_descriptionReference.owns xml_boolean, lod1ImplicitRepresentation.ImplicitGeometry.gml_descriptionReference.nilReason xml_buffer, lod1ImplicitRepresentation.ImplicitGeometry.gml_descriptionReference.gml_remoteSchema xml_buffer, lod1ImplicitRepresentation.ImplicitGeometry.gml_descriptionReference.xlink_href xml_buffer,
      lod1ImplicitRepresentation.ImplicitGeometry.gml_descriptionReference.xlink_title xml_buffer, lod1ImplicitRepresentation.ImplicitGeometry.gml_identifier xml_buffer, lod1ImplicitRepresentation.ImplicitGeometry.gml_identifier.codeSpace xml_buffer, lod1ImplicitRepresentation.ImplicitGeometry.gml_name{} xml_buffer, lod1ImplicitRepresentation.ImplicitGeometry.gml_name{}.codeSpace xml_buffer, lod1ImplicitRepresentation.ImplicitGeometry.transformationMatrix xml_buffer, lod1ImplicitRepresentation.ImplicitGeometry.mimeType xml_buffer, lod1ImplicitRepresentation.ImplicitGeometry.mimeType.codeSpace xml_buffer, lod1ImplicitRepresentation.ImplicitGeometry.libraryObject xml_buffer, lod1ImplicitRepresentation.ImplicitGeometry.referencePoint xml_geometry, lod1ImplicitRepresentation.ImplicitGeometry.relativeGeometry xml_geometry, lod1ImplicitRepresentation.ImplicitGeometry.appearance{}.nilReason xml_buffer, lod1ImplicitRepresentation.ImplicitGeometry.appearance{}.gml_remoteSchema xml_buffer, lod1ImplicitRepresentation.ImplicitGeometry.appearance{}.xlink_href xml_buffer, lod1ImplicitRepresentation.ImplicitGeometry.appearance{}.xlink_title xml_buffer, lod1ImplicitRepresentation.ImplicitGeometry.appearance{}.owns xml_boolean, lod2ImplicitRepresentation.ImplicitGeometry.gml_id xml_buffer, lod2ImplicitRepresentation.ImplicitGeometry.gml_metaDataProperty{}.about xml_buffer, lod2ImplicitRepresentation.ImplicitGeometry.gml_metaDataProperty{}.nilReason xml_buffer, lod2ImplicitRepresentation.ImplicitGeometry.gml_metaDataProperty{}.gml_remoteSchema xml_buffer, lod2ImplicitRepresentation.ImplicitGeometry.gml_metaDataProperty{}.xlink_href xml_buffer, lod2ImplicitRepresentation.ImplicitGeometry.gml_metaDataProperty{}.xlink_title xml_buffer, lod2ImplicitRepresentation.ImplicitGeometry.gml_metaDataProperty{}.gml_GenericMetaData xml_xml, lod2ImplicitRepresentation.ImplicitGeometry.gml_metaDataProperty{}.gml_GenericMetaData.gml_id xml_buffer, lod2ImplicitRepresentation.ImplicitGeometry.gml_description xml_buffer, lod2ImplicitRepresentation.ImplicitGeometry.gml_description.nilReason xml_buffer, lod2ImplicitRepresentation.ImplicitGeometry.gml_description.gml_remoteSchema xml_buffer, lod2ImplicitRepresentation.ImplicitGeometry.gml_description.xlink_href xml_buffer, lod2ImplicitRepresentation.ImplicitGeometry.gml_description.xlink_title xml_buffer, lod2ImplicitRepresentation.ImplicitGeometry.gml_descriptionReference.owns xml_boolean,
      lod2ImplicitRepresentation.ImplicitGeometry.gml_descriptionReference.nilReason xml_buffer, lod2ImplicitRepresentation.ImplicitGeometry.gml_descriptionReference.gml_remoteSchema xml_buffer, lod2ImplicitRepresentation.ImplicitGeometry.gml_descriptionReference.xlink_href xml_buffer, lod2ImplicitRepresentation.ImplicitGeometry.gml_descriptionReference.xlink_title xml_buffer, lod2ImplicitRepresentation.ImplicitGeometry.gml_identifier xml_buffer, lod2ImplicitRepresentation.ImplicitGeometry.gml_identifier.codeSpace xml_buffer, lod2ImplicitRepresentation.ImplicitGeometry.gml_name{} xml_buffer, lod2ImplicitRepresentation.ImplicitGeometry.gml_name{}.codeSpace xml_buffer, lod2ImplicitRepresentation.ImplicitGeometry.transformationMatrix xml_buffer, lod2ImplicitRepresentation.ImplicitGeometry.mimeType xml_buffer, lod2ImplicitRepresentation.ImplicitGeometry.mimeType.codeSpace xml_buffer, lod2ImplicitRepresentation.ImplicitGeometry.libraryObject xml_buffer, lod2ImplicitRepresentation.ImplicitGeometry.referencePoint xml_geometry, lod2ImplicitRepresentation.ImplicitGeometry.relativeGeometry xml_geometry, lod2ImplicitRepresentation.ImplicitGeometry.appearance{}.nilReason xml_buffer, lod2ImplicitRepresentation.ImplicitGeometry.appearance{}.gml_remoteSchema xml_buffer, lod2ImplicitRepresentation.ImplicitGeometry.appearance{}.xlink_href xml_buffer, lod2ImplicitRepresentation.ImplicitGeometry.appearance{}.xlink_title xml_buffer, lod2ImplicitRepresentation.ImplicitGeometry.appearance{}.owns xml_boolean, lod3ImplicitRepresentation.ImplicitGeometry.gml_id xml_buffer, lod3ImplicitRepresentation.ImplicitGeometry.gml_metaDataProperty{}.about xml_buffer, lod3ImplicitRepresentation.ImplicitGeometry.gml_metaDataProperty{}.nilReason xml_buffer, lod3ImplicitRepresentation.ImplicitGeometry.gml_metaDataProperty{}.gml_remoteSchema xml_buffer, lod3ImplicitRepresentation.ImplicitGeometry.gml_metaDataProperty{}.xlink_href xml_buffer, lod3ImplicitRepresentation.ImplicitGeometry.gml_metaDataProperty{}.xlink_title xml_buffer, lod3ImplicitRepresentation.ImplicitGeometry.gml_metaDataProperty{}.gml_GenericMetaData xml_xml, lod3ImplicitRepresentation.ImplicitGeometry.gml_metaDataProperty{}.gml_GenericMetaData.gml_id xml_buffer, lod3ImplicitRepresentation.ImplicitGeometry.gml_description xml_buffer, lod3ImplicitRepresentation.ImplicitGeometry.gml_description.nilReason xml_buffer, lod3ImplicitRepresentation.ImplicitGeometry.gml_description.gml_remoteSchema xml_buffer,
      lod3ImplicitRepresentation.ImplicitGeometry.gml_description.xlink_href xml_buffer, lod3ImplicitRepresentation.ImplicitGeometry.gml_description.xlink_title xml_buffer, lod3ImplicitRepresentation.ImplicitGeometry.gml_descriptionReference.owns xml_boolean, lod3ImplicitRepresentation.ImplicitGeometry.gml_descriptionReference.nilReason xml_buffer, lod3ImplicitRepresentation.ImplicitGeometry.gml_descriptionReference.gml_remoteSchema xml_buffer, lod3ImplicitRepresentation.ImplicitGeometry.gml_descriptionReference.xlink_href xml_buffer, lod3ImplicitRepresentation.ImplicitGeometry.gml_descriptionReference.xlink_title xml_buffer, lod3ImplicitRepresentation.ImplicitGeometry.gml_identifier xml_buffer, lod3ImplicitRepresentation.ImplicitGeometry.gml_identifier.codeSpace xml_buffer, lod3ImplicitRepresentation.ImplicitGeometry.gml_name{} xml_buffer, lod3ImplicitRepresentation.ImplicitGeometry.gml_name{}.codeSpace xml_buffer, lod3ImplicitRepresentation.ImplicitGeometry.transformationMatrix xml_buffer, lod3ImplicitRepresentation.ImplicitGeometry.mimeType xml_buffer, lod3ImplicitRepresentation.ImplicitGeometry.mimeType.codeSpace xml_buffer, lod3ImplicitRepresentation.ImplicitGeometry.libraryObject xml_buffer, lod3ImplicitRepresentation.ImplicitGeometry.referencePoint xml_geometry, lod3ImplicitRepresentation.ImplicitGeometry.relativeGeometry xml_geometry, lod3ImplicitRepresentation.ImplicitGeometry.appearance{}.nilReason xml_buffer, lod3ImplicitRepresentation.ImplicitGeometry.appearance{}.gml_remoteSchema xml_buffer, lod3ImplicitRepresentation.ImplicitGeometry.appearance{}.xlink_href xml_buffer, lod3ImplicitRepresentation.ImplicitGeometry.appearance{}.xlink_title xml_buffer, lod3ImplicitRepresentation.ImplicitGeometry.appearance{}.owns xml_boolean, adeOfAbstractOccupiedSpace{} xml_xml, adeOfAbstractInstallation{} xml_xml, adeOfBuildingInstallation{} xml_xml
BuildingRoom (writer GML_1)
    attributes: gml_metaDataProperty{}.about xml_buffer, gml_metaDataProperty{}.nilReason xml_buffer, gml_metaDataProperty{}.gml_remoteSchema xml_buffer, gml_metaDataProperty{}.xlink_href xml_buffer, gml_metaDataProperty{}.xlink_title xml_buffer, gml_description xml_buffer, gml_description.nilReason xml_buffer, gml_description.gml_remoteSchema xml_buffer, gml_description.xlink_href xml_buffer, gml_description.xlink_title xml_buffer, gml_descriptionReference.owns xml_boolean, gml_descriptionReference.nilReason xml_buffer, gml_descriptionReference.gml_remoteSchema xml_buffer, gml_descriptionReference.xlink_href xml_buffer, gml_descriptionReference.xlink_title xml_buffer, gml_identifier xml_buffer, gml_identifier.codeSpace xml_buffer, gml_name{} xml_buffer, gml_name{}.codeSpace xml_buffer, gml_boundedBy xml_geometry, gml_location xml_geometry, creationDate xml_datetime, terminationDate xml_datetime, validFrom xml_datetime, validTo xml_datetime, generalizesTo{}.owns xml_boolean, generalizesTo{}.nilReason xml_buffer, generalizesTo{}.gml_remoteSchema xml_buffer, generalizesTo{}.xlink_href xml_buffer, generalizesTo{}.xlink_title xml_buffer,
      relativeToTerrain xml_char(33), relativeToWater xml_char(38), relatedTo{}.nilReason xml_buffer, relatedTo{}.gml_remoteSchema xml_buffer, relatedTo{}.xlink_href xml_buffer, relatedTo{}.xlink_title xml_buffer, relatedTo{}.owns xml_boolean, appearance{}.nilReason xml_buffer, appearance{}.gml_remoteSchema xml_buffer, appearance{}.xlink_href xml_buffer, appearance{}.xlink_title xml_buffer, appearance{}.owns xml_boolean, dynamizer{}.nilReason xml_buffer, dynamizer{}.gml_remoteSchema xml_buffer, dynamizer{}.xlink_href xml_buffer, dynamizer{}.xlink_title xml_buffer, dynamizer{}.owns xml_boolean, spaceType xml_char(8), lod0Point xml_geometry, lod0MultiSurface xml_geometry, lod1Solid xml_geometry, lod2Solid xml_geometry, lod2MultiSurface xml_geometry, lod2MultiCurve xml_geometry, boundary{}.nilReason xml_buffer, boundary{}.gml_remoteSchema xml_buffer, boundary{}.xlink_href xml_buffer, boundary{}.xlink_title xml_buffer, boundary{}.owns xml_boolean, lod3Solid xml_geometry,
      lod3MultiSurface xml_geometry, lod3MultiCurve xml_geometry, lod1TerrainIntersectionCurve xml_geometry, lod2TerrainIntersectionCurve xml_geometry, lod3TerrainIntersectionCurve xml_geometry, pointCloud.nilReason xml_buffer, pointCloud.gml_remoteSchema xml_buffer, pointCloud.xlink_href xml_buffer, pointCloud.xlink_title xml_buffer, pointCloud.owns xml_boolean, class xml_buffer, class.codeSpace xml_buffer, function{} xml_buffer, function{}.codeSpace xml_buffer, usage{} xml_buffer, usage{}.codeSpace xml_buffer, buildingFurniture{}.nilReason xml_buffer, buildingFurniture{}.gml_remoteSchema xml_buffer, buildingFurniture{}.xlink_href xml_buffer, buildingFurniture{}.xlink_title xml_buffer, buildingFurniture{}.owns xml_boolean, buildingInstallation{}.nilReason xml_buffer, buildingInstallation{}.gml_remoteSchema xml_buffer, buildingInstallation{}.xlink_href xml_buffer, buildingInstallation{}.xlink_title xml_buffer, buildingInstallation{}.owns xml_boolean, gml_metaDataProperty{}.gml_GenericMetaData xml_xml, gml_metaDataProperty{}.gml_GenericMetaData.gml_id xml_buffer, gml_priorityLocation xml_geometry, externalReference{}.ExternalReference.targetResource xml_buffer,
      externalReference{}.ExternalReference.informationSystem xml_buffer, externalReference{}.ExternalReference.relationType xml_buffer, relatedTo{}.CityObjectRelation.gml_id xml_buffer, relatedTo{}.CityObjectRelation.gml_metaDataProperty{}.about xml_buffer, relatedTo{}.CityObjectRelation.gml_metaDataProperty{}.nilReason xml_buffer, relatedTo{}.CityObjectRelation.gml_metaDataProperty{}.gml_remoteSchema xml_buffer, relatedTo{}.CityObjectRelation.gml_metaDataProperty{}.xlink_href xml_buffer, relatedTo{}.CityObjectRelation.gml_metaDataProperty{}.xlink_title xml_buffer, relatedTo{}.CityObjectRelation.gml_metaDataProperty{}.gml_GenericMetaData xml_xml, relatedTo{}.CityObjectRelation.gml_metaDataProperty{}.gml_GenericMetaData.gml_id xml_buffer, relatedTo{}.CityObjectRelation.gml_description xml_buffer, relatedTo{}.CityObjectRelation.gml_description.nilReason xml_buffer, relatedTo{}.CityObjectRelation.gml_description.gml_remoteSchema xml_buffer, relatedTo{}.CityObjectRelation.gml_description.xlink_href xml_buffer, relatedTo{}.CityObjectRelation.gml_description.xlink_title xml_buffer, relatedTo{}.CityObjectRelation.gml_descriptionReference.owns xml_boolean, relatedTo{}.CityObjectRelation.gml_descriptionReference.nilReason xml_buffer, relatedTo{}.CityObjectRelation.gml_descriptionReference.gml_remoteSchema xml_buffer, relatedTo{}.CityObjectRelation.gml_descriptionReference.xlink_href xml_buffer, relatedTo{}.CityObjectRelation.gml_descriptionReference.xlink_title xml_buffer, relatedTo{}.CityObjectRelation.gml_identifier xml_buffer, relatedTo{}.CityObjectRelation.gml_identifier.codeSpace xml_buffer, relatedTo{}.CityObjectRelation.gml_name{} xml_buffer, relatedTo{}.CityObjectRelation.gml_name{}.codeSpace xml_buffer, relatedTo{}.CityObjectRelation.relatedTo.nilReason xml_buffer, relatedTo{}.CityObjectRelation.relatedTo.gml_remoteSchema xml_buffer, relatedTo{}.CityObjectRelation.relatedTo.xlink_href xml_buffer, relatedTo{}.CityObjectRelation.relatedTo.xlink_title xml_buffer, relatedTo{}.CityObjectRelation.relatedTo.owns xml_boolean, genericAttribute{}.DateAttribute.name xml_buffer,
      genericAttribute{}.DateAttribute.value xml_date, genericAttribute{}.DoubleAttribute.name xml_buffer, genericAttribute{}.DoubleAttribute.value xml_real64, genericAttribute{}.GenericAttributeSet.name xml_buffer, genericAttribute{}.GenericAttributeSet.codeSpace xml_buffer, genericAttribute{}.GenericAttributeSet.genericAttribute{}.DateAttribute xml_xml, genericAttribute{}.GenericAttributeSet.genericAttribute{}.DoubleAttribute xml_xml, genericAttribute{}.GenericAttributeSet.genericAttribute{}.GenericAttributeSet xml_xml, genericAttribute{}.GenericAttributeSet.genericAttribute{}.IntAttribute xml_xml, genericAttribute{}.GenericAttributeSet.genericAttribute{}.MeasureAttribute xml_xml, genericAttribute{}.GenericAttributeSet.genericAttribute{}.StringAttribute xml_xml, genericAttribute{}.GenericAttributeSet.genericAttribute{}.UriAttribute xml_xml, genericAttribute{}.IntAttribute.name xml_buffer, genericAttribute{}.IntAttribute.value xml_int64, genericAttribute{}.MeasureAttribute.name xml_buffer, genericAttribute{}.MeasureAttribute.value xml_real64, genericAttribute{}.MeasureAttribute.value.uom xml_buffer, genericAttribute{}.StringAttribute.name xml_buffer, genericAttribute{}.StringAttribute.value xml_buffer, genericAttribute{}.UriAttribute.name xml_buffer, genericAttribute{}.UriAttribute.value xml_buffer, volume{}.QualifiedVolume.volume xml_real64, volume{}.QualifiedVolume.volume.uom xml_buffer, area{}.QualifiedArea.area xml_real64, area{}.QualifiedArea.area.uom xml_buffer, roomHeight{}.RoomHeight.highReference xml_buffer, roomHeight{}.RoomHeight.lowReference xml_buffer, roomHeight{}.RoomHeight.status xml_char(9), roomHeight{}.RoomHeight.value xml_real64, roomHeight{}.RoomHeight.value.uom xml_buffer,
      adeOfAbstractFeature{} xml_xml, adeOfAbstractFeatureWithLifespan{} xml_xml, relatedTo{}.CityObjectRelation.genericAttribute{}.CodeAttribute.name xml_buffer, relatedTo{}.CityObjectRelation.genericAttribute{}.CodeAttribute.value xml_buffer, relatedTo{}.CityObjectRelation.genericAttribute{}.CodeAttribute.value.codeSpace xml_buffer, relatedTo{}.CityObjectRelation.genericAttribute{}.DateAttribute.name xml_buffer, relatedTo{}.CityObjectRelation.genericAttribute{}.DateAttribute.value xml_date, relatedTo{}.CityObjectRelation.genericAttribute{}.DoubleAttribute.name xml_buffer, relatedTo{}.CityObjectRelation.genericAttribute{}.DoubleAttribute.value xml_real64, relatedTo{}.CityObjectRelation.genericAttribute{}.GenericAttributeSet.name xml_buffer, relatedTo{}.CityObjectRelation.genericAttribute{}.GenericAttributeSet.codeSpace xml_buffer, relatedTo{}.CityObjectRelation.genericAttribute{}.GenericAttributeSet.genericAttribute{}.CodeAttribute xml_xml, relatedTo{}.CityObjectRelation.genericAttribute{}.GenericAttributeSet.genericAttribute{}.DateAttribute xml_xml, relatedTo{}.CityObjectRelation.genericAttribute{}.GenericAttributeSet.genericAttribute{}.DoubleAttribute xml_xml, relatedTo{}.CityObjectRelation.genericAttribute{}.GenericAttributeSet.genericAttribute{}.GenericAttributeSet xml_xml, relatedTo{}.CityObjectRelation.genericAttribute{}.GenericAttributeSet.genericAttribute{}.IntAttribute xml_xml, relatedTo{}.CityObjectRelation.genericAttribute{}.GenericAttributeSet.genericAttribute{}.MeasureAttribute xml_xml, relatedTo{}.CityObjectRelation.genericAttribute{}.GenericAttributeSet.genericAttribute{}.StringAttribute xml_xml, relatedTo{}.CityObjectRelation.genericAttribute{}.GenericAttributeSet.genericAttribute{}.UriAttribute xml_xml, relatedTo{}.CityObjectRelation.genericAttribute{}.IntAttribute.name xml_buffer, relatedTo{}.CityObjectRelation.genericAttribute{}.IntAttribute.value xml_int64, relatedTo{}.CityObjectRelation.genericAttribute{}.MeasureAttribute.name xml_buffer, relatedTo{}.CityObjectRelation.genericAttribute{}.MeasureAttribute.value xml_real64, relatedTo{}.CityObjectRelation.genericAttribute{}.MeasureAttribute.value.uom xml_buffer, relatedTo{}.CityObjectRelation.genericAttribute{}.StringAttribute.name xml_buffer, relatedTo{}.CityObjectRelation.genericAttribute{}.StringAttribute.value xml_buffer, relatedTo{}.CityObjectRelation.genericAttribute{}.UriAttribute.name xml_buffer, relatedTo{}.CityObjectRelation.genericAttribute{}.UriAttribute.value xml_buffer, relatedTo{}.CityObjectRelation.relationType xml_buffer, relatedTo{}.CityObjectRelation.relationType.codeSpace xml_buffer,
      genericAttribute{}.CodeAttribute.name xml_buffer, genericAttribute{}.CodeAttribute.value xml_buffer, genericAttribute{}.CodeAttribute.value.codeSpace xml_buffer, genericAttribute{}.GenericAttributeSet.genericAttribute{}.CodeAttribute xml_xml, adeOfAbstractCityObject{} xml_xml, volume{}.QualifiedVolume.typeOfVolume xml_buffer, volume{}.QualifiedVolume.typeOfVolume.codeSpace xml_buffer, area{}.QualifiedArea.typeOfArea xml_buffer, area{}.QualifiedArea.typeOfArea.codeSpace xml_buffer, lod0MultiCurve xml_geometry, adeOfAbstractSpace{} xml_xml, adeOfAbstractPhysicalSpace{} xml_xml, adeOfAbstractUnoccupiedSpace{} xml_xml, roomHeight{}.RoomHeight.highReference.codeSpace xml_buffer, roomHeight{}.RoomHeight.lowReference.codeSpace xml_buffer, adeOfBuildingRoom{} xml_xml
Storey (writer GML_1)
    attributes: gml_metaDataProperty{}.about xml_buffer, gml_metaDataProperty{}.nilReason xml_buffer, gml_metaDataProperty{}.gml_remoteSchema xml_buffer, gml_metaDataProperty{}.xlink_href xml_buffer, gml_metaDataProperty{}.xlink_title xml_buffer, gml_description xml_buffer, gml_description.nilReason xml_buffer, gml_description.gml_remoteSchema xml_buffer, gml_description.xlink_href xml_buffer, gml_description.xlink_title xml_buffer, gml_descriptionReference.owns xml_boolean, gml_descriptionReference.nilReason xml_buffer, gml_descriptionReference.gml_remoteSchema xml_buffer, gml_descriptionReference.xlink_href xml_buffer, gml_descriptionReference.xlink_title xml_buffer, gml_identifier xml_buffer, gml_identifier.codeSpace xml_buffer, gml_name{} xml_buffer, gml_name{}.codeSpace xml_buffer, gml_boundedBy xml_geometry, gml_location xml_geometry, creationDate xml_datetime, terminationDate xml_datetime, validFrom xml_datetime, validTo xml_datetime, generalizesTo{}.owns xml_boolean, generalizesTo{}.nilReason xml_buffer, generalizesTo{}.gml_remoteSchema xml_buffer, generalizesTo{}.xlink_href xml_buffer, generalizesTo{}.xlink_title xml_buffer,
      relativeToTerrain xml_char(33), relativeToWater xml_char(38), relatedTo{}.owns xml_boolean, relatedTo{}.nilReason xml_buffer, relatedTo{}.gml_remoteSchema xml_buffer, relatedTo{}.xlink_href xml_buffer, relatedTo{}.xlink_title xml_buffer, appearance{}.nilReason xml_buffer, appearance{}.gml_remoteSchema xml_buffer, appearance{}.xlink_href xml_buffer, appearance{}.xlink_title xml_buffer, appearance{}.owns xml_boolean, dynamizer{}.nilReason xml_buffer, dynamizer{}.gml_remoteSchema xml_buffer, dynamizer{}.xlink_href xml_buffer, dynamizer{}.xlink_title xml_buffer, dynamizer{}.owns xml_boolean, spaceType xml_char(8), lod0Point xml_geometry, lod0MultiSurface xml_geometry, lod1Solid xml_geometry, lod2Solid xml_geometry, lod2MultiSurface xml_geometry, lod2MultiCurve xml_geometry, boundary{}.nilReason xml_buffer, boundary{}.gml_remoteSchema xml_buffer, boundary{}.xlink_href xml_buffer, boundary{}.xlink_title xml_buffer, boundary{}.owns xml_boolean, lod3Solid xml_geometry,
      lod3MultiSurface xml_geometry, lod3MultiCurve xml_geometry, class xml_buffer, class.codeSpace xml_buffer, function{} xml_buffer, function{}.codeSpace xml_buffer, usage{} xml_buffer, usage{}.codeSpace xml_buffer, sortKey xml_real64, buildingUnit{}.owns xml_boolean, buildingUnit{}.nilReason xml_buffer, buildingUnit{}.gml_remoteSchema xml_buffer, buildingUnit{}.xlink_href xml_buffer, buildingUnit{}.xlink_title xml_buffer, buildingConstructiveElement{}.owns xml_boolean, buildingConstructiveElement{}.nilReason xml_buffer, buildingConstructiveElement{}.gml_remoteSchema xml_buffer, buildingConstructiveElement{}.xlink_href xml_buffer, buildingConstructiveElement{}.xlink_title xml_buffer, buildingFurniture{}.nilReason xml_buffer, buildingFurniture{}.gml_remoteSchema xml_buffer, buildingFurniture{}.xlink_href xml_buffer, buildingFurniture{}.xlink_title xml_buffer, buildingFurniture{}.owns xml_boolean, buildingInstallation{}.nilReason xml_buffer, buildingInstallation{}.gml_remoteSchema xml_buffer, buildingInstallation{}.xlink_href xml_buffer, buildingInstallation{}.xlink_title xml_buffer, buildingInstallation{}.owns xml_boolean, buildingRoom{}.owns xml_boolean,
      buildingRoom{}.nilReason xml_buffer, buildingRoom{}.gml_remoteSchema xml_buffer, buildingRoom{}.xlink_href xml_buffer, buildingRoom{}.xlink_title xml_buffer, gml_metaDataProperty{}.gml_GenericMetaData xml_xml, gml_metaDataProperty{}.gml_GenericMetaData.gml_id xml_buffer, gml_priorityLocation xml_geometry, externalReference{}.ExternalReference.targetResource xml_buffer, externalReference{}.ExternalReference.informationSystem xml_buffer, externalReference{}.ExternalReference.relationType xml_buffer, relatedTo{}.CityObjectRelation.gml_id xml_buffer, relatedTo{}.CityObjectRelation.gml_metaDataProperty{}.about xml_buffer, relatedTo{}.CityObjectRelation.gml_metaDataProperty{}.nilReason xml_buffer, relatedTo{}.CityObjectRelation.gml_metaDataProperty{}.gml_remoteSchema xml_buffer, relatedTo{}.CityObjectRelation.gml_metaDataProperty{}.xlink_href xml_buffer, relatedTo{}.CityObjectRelation.gml_metaDataProperty{}.xlink_title xml_buffer, relatedTo{}.CityObjectRelation.gml_metaDataProperty{}.gml_GenericMetaData xml_xml, relatedTo{}.CityObjectRelation.gml_metaDataProperty{}.gml_GenericMetaData.gml_id xml_buffer, relatedTo{}.CityObjectRelation.gml_description xml_buffer, relatedTo{}.CityObjectRelation.gml_description.nilReason xml_buffer, relatedTo{}.CityObjectRelation.gml_description.gml_remoteSchema xml_buffer, relatedTo{}.CityObjectRelation.gml_description.xlink_href xml_buffer, relatedTo{}.CityObjectRelation.gml_description.xlink_title xml_buffer, relatedTo{}.CityObjectRelation.gml_descriptionReference.owns xml_boolean, relatedTo{}.CityObjectRelation.gml_descriptionReference.nilReason xml_buffer, relatedTo{}.CityObjectRelation.gml_descriptionReference.gml_remoteSchema xml_buffer, relatedTo{}.CityObjectRelation.gml_descriptionReference.xlink_href xml_buffer, relatedTo{}.CityObjectRelation.gml_descriptionReference.xlink_title xml_buffer, relatedTo{}.CityObjectRelation.gml_identifier xml_buffer, relatedTo{}.CityObjectRelation.gml_identifier.codeSpace xml_buffer,
      relatedTo{}.CityObjectRelation.gml_name{} xml_buffer, relatedTo{}.CityObjectRelation.gml_name{}.codeSpace xml_buffer, relatedTo{}.CityObjectRelation.relatedTo.nilReason xml_buffer, relatedTo{}.CityObjectRelation.relatedTo.gml_remoteSchema xml_buffer, relatedTo{}.CityObjectRelation.relatedTo.xlink_href xml_buffer, relatedTo{}.CityObjectRelation.relatedTo.xlink_title xml_buffer, relatedTo{}.CityObjectRelation.relatedTo.owns xml_boolean, genericAttribute{}.DateAttribute.name xml_buffer, genericAttribute{}.DateAttribute.value xml_date, genericAttribute{}.DoubleAttribute.name xml_buffer, genericAttribute{}.DoubleAttribute.value xml_real64, genericAttribute{}.GenericAttributeSet.name xml_buffer, genericAttribute{}.GenericAttributeSet.codeSpace xml_buffer, genericAttribute{}.GenericAttributeSet.genericAttribute{}.DateAttribute xml_xml, genericAttribute{}.GenericAttributeSet.genericAttribute{}.DoubleAttribute xml_xml, genericAttribute{}.GenericAttributeSet.genericAttribute{}.GenericAttributeSet xml_xml, genericAttribute{}.GenericAttributeSet.genericAttribute{}.IntAttribute xml_xml, genericAttribute{}.GenericAttributeSet.genericAttribute{}.MeasureAttribute xml_xml, genericAttribute{}.GenericAttributeSet.genericAttribute{}.StringAttribute xml_xml, genericAttribute{}.GenericAttributeSet.genericAttribute{}.UriAttribute xml_xml, genericAttribute{}.IntAttribute.name xml_buffer, genericAttribute{}.IntAttribute.value xml_int64, genericAttribute{}.MeasureAttribute.name xml_buffer, genericAttribute{}.MeasureAttribute.value xml_real64, genericAttribute{}.MeasureAttribute.value.uom xml_buffer, genericAttribute{}.StringAttribute.name xml_buffer, genericAttribute{}.StringAttribute.value xml_buffer, genericAttribute{}.UriAttribute.name xml_buffer, genericAttribute{}.UriAttribute.value xml_buffer, volume{}.QualifiedVolume.volume xml_real64,
      volume{}.QualifiedVolume.volume.uom xml_buffer, area{}.QualifiedArea.area xml_real64, area{}.QualifiedArea.area.uom xml_buffer, elevation{}.Elevation.elevationReference xml_buffer, elevation{}.Elevation.elevationValue xml_buffer, elevation{}.Elevation.elevationValue.srsName xml_buffer, elevation{}.Elevation.elevationValue.srsDimension xml_uint64, elevation{}.Elevation.elevationValue.axisLabels xml_buffer, elevation{}.Elevation.elevationValue.uomLabels xml_buffer, adeOfAbstractFeature{} xml_xml, adeOfAbstractFeatureWithLifespan{} xml_xml, relatedTo{}.CityObjectRelation.genericAttribute{}.CodeAttribute.name xml_buffer, relatedTo{}.CityObjectRelation.genericAttribute{}.CodeAttribute.value xml_buffer, relatedTo{}.CityObjectRelation.genericAttribute{}.CodeAttribute.value.codeSpace xml_buffer, relatedTo{}.CityObjectRelation.genericAttribute{}.DateAttribute.name xml_buffer, relatedTo{}.CityObjectRelation.genericAttribute{}.DateAttribute.value xml_date, relatedTo{}.CityObjectRelation.genericAttribute{}.DoubleAttribute.name xml_buffer, relatedTo{}.CityObjectRelation.genericAttribute{}.DoubleAttribute.value xml_real64, relatedTo{}.CityObjectRelation.genericAttribute{}.GenericAttributeSet.name xml_buffer, relatedTo{}.CityObjectRelation.genericAttribute{}.GenericAttributeSet.codeSpace xml_buffer, relatedTo{}.CityObjectRelation.genericAttribute{}.GenericAttributeSet.genericAttribute{}.CodeAttribute xml_xml, relatedTo{}.CityObjectRelation.genericAttribute{}.GenericAttributeSet.genericAttribute{}.DateAttribute xml_xml, relatedTo{}.CityObjectRelation.genericAttribute{}.GenericAttributeSet.genericAttribute{}.DoubleAttribute xml_xml, relatedTo{}.CityObjectRelation.genericAttribute{}.GenericAttributeSet.genericAttribute{}.GenericAttributeSet xml_xml, relatedTo{}.CityObjectRelation.genericAttribute{}.GenericAttributeSet.genericAttribute{}.IntAttribute xml_xml, relatedTo{}.CityObjectRelation.genericAttribute{}.GenericAttributeSet.genericAttribute{}.MeasureAttribute xml_xml, relatedTo{}.CityObjectRelation.genericAttribute{}.GenericAttributeSet.genericAttribute{}.StringAttribute xml_xml, relatedTo{}.CityObjectRelation.genericAttribute{}.GenericAttributeSet.genericAttribute{}.UriAttribute xml_xml, relatedTo{}.CityObjectRelation.genericAttribute{}.IntAttribute.name xml_buffer, relatedTo{}.CityObjectRelation.genericAttribute{}.IntAttribute.value xml_int64,
      relatedTo{}.CityObjectRelation.genericAttribute{}.MeasureAttribute.name xml_buffer, relatedTo{}.CityObjectRelation.genericAttribute{}.MeasureAttribute.value xml_real64, relatedTo{}.CityObjectRelation.genericAttribute{}.MeasureAttribute.value.uom xml_buffer, relatedTo{}.CityObjectRelation.genericAttribute{}.StringAttribute.name xml_buffer, relatedTo{}.CityObjectRelation.genericAttribute{}.StringAttribute.value xml_buffer, relatedTo{}.CityObjectRelation.genericAttribute{}.UriAttribute.name xml_buffer, relatedTo{}.CityObjectRelation.genericAttribute{}.UriAttribute.value xml_buffer, relatedTo{}.CityObjectRelation.relationType xml_buffer, relatedTo{}.CityObjectRelation.relationType.codeSpace xml_buffer, genericAttribute{}.CodeAttribute.name xml_buffer, genericAttribute{}.CodeAttribute.value xml_buffer, genericAttribute{}.CodeAttribute.value.codeSpace xml_buffer, genericAttribute{}.GenericAttributeSet.genericAttribute{}.CodeAttribute xml_xml, adeOfAbstractCityObject{} xml_xml, volume{}.QualifiedVolume.typeOfVolume xml_buffer, volume{}.QualifiedVolume.typeOfVolume.codeSpace xml_buffer, area{}.QualifiedArea.typeOfArea xml_buffer, area{}.QualifiedArea.typeOfArea.codeSpace xml_buffer, lod0MultiCurve xml_geometry, adeOfAbstractSpace{} xml_xml, adeOfAbstractLogicalSpace{} xml_xml, elevation{}.Elevation.elevationReference.codeSpace xml_buffer, adeOfAbstractBuildingSubdivision{} xml_xml, adeOfStorey{} xml_xml

Bookmark: Building
AttributeRenamer
    ATTR_TABLE:
      RENAME_SET_DEFAULT Name > gml_name{0}
      RENAME_SET_DEFAULT Description > gml_description
    -> AttributeCreator
AttributeCreator
    ATTR_TABLE:
      SET_TO gml_id = id_@UUID()
      SET_TO spaceType = closed
      SET_TO genericAttribute{0}.StringAttribute.name = IFC_GlobalId
      SET_TO genericAttribute{0}.StringAttribute.value = @Value(GlobalId)
      SET_TO genericAttribute{1}.StringAttribute.name = IFC_ObjectType
      SET_TO genericAttribute{1}.StringAttribute.value = @Value(ObjectType)
      SET_TO class = 1000
      SET_TO function{0} = 1000
    -> FeatureMerger_8 [REQUESTOR]
AttributeKeeper_11
    CREATE_BULK_MODE_FEATURES = No
    KEEP_ATTRS = gml_id
    -> AttributeRenamer_0
Note: Set gml_parent_id
AttributeRenamer_0
    ATTR_TABLE = RENAME_SET_DEFAULT gml_id > gml_parent_id
    -> FeatureMerger_1 [SUPPLIER]

Bookmark: Storey
AttributeRenamer_5
    ATTR_TABLE = RENAME_SET_DEFAULT Name > gml_name{0}
    -> UUIDGenerator_8
UUIDGenerator_8
    UUID_ATTR = _uuid
    -> AttributeCreator_4
AttributeCreator_4
    ATTR_TABLE:
      SET_TO citygml_feature_role = storey
      SET_TO gml_id = id_@UUID()
      SET_TO gml_id_storey_ref = @Value(GlobalId)
      SET_TO genericAttribute{0}.StringAttribute.name = IFC_GlobalId
      SET_TO genericAttribute{0}.StringAttribute.value = @Value(GlobalId)
      SET_TO genericAttribute{1}.StringAttribute.name = IFC_CompositionType
      SET_TO genericAttribute{1}.StringAttribute.value = @Value(CompositionType)
      SET_TO genericAttribute{2}.StringAttribute.name = IFC_LongName
      SET_TO genericAttribute{2}.StringAttribute.value = @Value(LongName)
      SET_TO genericAttribute{3}.StringAttribute.name = IFC_Elevation
      SET_TO genericAttribute{3}.StringAttribute.value = @Value(Elevation)
      SET_TO class = 1000
    -> FeatureMerger [REQUESTOR]

Bookmark: Revit Reader
Site (reader REVIT_1)
    attributes: element_id char(200), element_parent_id char(200), Name char(255), ObjectType char(255), RefElevation double, RefLatitude double, RefLongitude double, GlobalId char(200), Dimensions.Projected Area double, Dimensions.Surface Area double, Materials and Finishes.Material char(200), Phasing.Phase Created char(200)
    -> AttributeKeeper_3
Wall (reader REVIT_1)
    attributes: element_parent_id char(200), element_id char(200), GlobalId char(200), Name char(200), ObjectType char(200), Tag char(200), Analytical Properties.Roughness double, Analytical Properties.Absorptance double, BaseQuantities.GrossFootprintArea double, BaseQuantities.GrossSideArea double, BaseQuantities.GrossVolume double, BaseQuantities.Height double, BaseQuantities.Length double, BaseQuantities.Width double, Constraints.Base Constraint char(200), Constraints.Base Extension Distance double, Constraints.Base is Attached logical, Constraints.Base Offset double, Constraints.Location Line char(200), Constraints.Related to Mass logical, Constraints.Room Bounding logical, Constraints.Top Constraint char(200), Constraints.Top Extension Distance double, Constraints.Top is Attached logical, Constraints.Top Offset double, Constraints.Unconnected Height double, Construction.Function char(200), Construction.Width double, Construction.Wrapping at Ends char(200), Construction.Wrapping at Inserts char(200),
      Dimensions.Area double, Dimensions.Length double, Dimensions.Volume double, Graphics.Coarse Scale Fill Color integer, Graphics.Coarse Scale Fill Pattern char(200), Identity Data.Assembly Code char(200), Identity Data.Assembly Description char(200), Materials and Finishes.Structural Material char(200), Phasing.Phase Created char(200), Pset_WallCommon.ExtendToStructure logical, Pset_WallCommon.IsExternal logical, Pset_WallCommon.LoadBearing logical, Pset_WallCommon.Reference char(200), Structural.Enable Analytical Model logical, Structural.Structural logical, Structural.Structural Usage char(200), Pset_ManufacturerTypeInformation.Manufacturer char(200), Pset_ManufacturerTypeInformation.ModelLabel char(200), Pset_ManufacturerTypeInformation.ModelReference char(200), Pset_ManufacturerTypeInformation.ProductionYear char(200)
    -> AttributeKeeper_3
Slab (reader REVIT_1)
    attributes: element_parent_id char(200), element_id char(200), GlobalId char(200), Name char(200), ObjectType char(200), Tag char(200), OverallHeight double, OverallWidth double, Analytical Properties.Absorptance double, Analytical Properties.Roughness double, BaseQuantities.GrossArea double, BaseQuantities.GrossVolume double, BaseQuantities.Perimeter double, BaseQuantities.Width double, Constraints.Base Level char(200), Constraints.Base Offset From Level double, Constraints.Cutoff Offset double, Constraints.Height Offset From Level double, Constraints.Level char(200), Constraints.Related to Mass logical, Constraints.Room Bounding logical, Construction.Default Thickness double, Construction.Fascia Depth double, Construction.Function char(200), Construction.Maximum Ridge Height double, Construction.Rafter Cut char(200), Construction.Rafter or Truss char(200), Construction.Thickness double, Dimensions.Area double, Dimensions.Perimeter double,
      Dimensions.Slope double, Dimensions.Thickness double, Dimensions.Volume double, Graphics.Coarse Scale Fill Color double, Identity Data.Assembly Code char(200), Identity Data.Assembly Description char(200), Materials and Finishes.Structural Material char(200), Phasing.Phase Created char(200), Pset_RoofCommon.IsExternal logical, Pset_RoofCommon.ProjectedArea double, Pset_RoofCommon.Reference char(200), Pset_RoofCommon.TotalArea double, Pset_SlabCommon.IsExternal logical, Pset_SlabCommon.LoadBearing logical, Pset_SlabCommon.Reference char(200), Pset_ManufacturerTypeInformation.Manufacturer char(200), Pset_ManufacturerTypeInformation.ModelLabel char(200), Pset_ManufacturerTypeInformation.ModelReference char(200), Pset_ManufacturerTypeInformation.ProductionYear char(200)
    -> AttributeKeeper_3
Space (reader REVIT_1)
    attributes: element_parent_id char(200), element_id char(200), Name char(200), GlobalId char(200), LongName char(200), InteriorOrExteriorSpace char(200), BaseQuantities.GrossFloorArea double, BaseQuantities.GrossPerimeter double, BaseQuantities.GrossVolume double, BaseQuantities.Height double, BaseQuantities.NetFloorArea double, Constraints.Base Offset double, Constraints.Level char(200), Constraints.Limit Offset double, Constraints.Upper Limit char(200), Dimensions.Area double, Dimensions.Computation Height double, Dimensions.Perimeter double, Dimensions.Unbounded Height double, Phasing.Phase (utf-8) char(200), Pset_SpaceCommon.Reference (utf-8) char(200)
    -> AttributeKeeper_3

Bookmark: BuildingConstructiveElement
FeatureMerger_7
    ATTR_ACCUM_MODE = Merge Supplier
    ATTR_CONFLICT_RES = Use Requestor
    IGNORE_NULLS = No
    JOIN_KEYS = @Value(GlobalId) @Value(GlobalId) AUTO
    MERGE_TYPE = Attributes Only
    PROCESS_DUPS = NO
    REJECT_NULL_MISSING_KEYS = No
    SUPPLIERS_FIRST = No
    MERGED -> AttributeExposer
AttributeExposer
    ATTR_LIST = fme_feature_type
    -> AttributeValueMapper_9
AttributeValueMapper_9
    DEFAULT_VALUE = unknown
    DIRECTION = Forward (Source To Destination)
    LUT = Wall,IfcWallStandardCase,Beam,IfcBeam,Slab,IfcSlab,Member,IfcMember
    SRC = fme_feature_type
    VAL_ATTR = class
    -> AttributeCreator_10
AttributeCreator_10
    ATTR_TABLE:
      SET_TO citygml_lod_name = lod3Solid
      SET_TO citygml_feature_role = buildingConstructiveElement
      SET_TO gml_id_BCE_ref = @Value(GlobalId)
      SET_TO gml_id_BCE = id_@UUID()
      SET_TO genericAttribute{0}.StringAttribute.name = IFC_GlobalId
      SET_TO genericAttribute{0}.StringAttribute.value = @Value(GlobalId)
      SET_TO genericAttribute{1}.StringAttribute.name = IFC_Tag
      SET_TO genericAttribute{1}.StringAttribute.value = @Value(Tag)
    -> AttributeRenamer_1
    -> AttributeCreator_14
    -> AttributeKeeper_2
    -> AttributeCreator_1
AttributeCreator_1
    ATTR_TABLE:
      SET_TO genericAttribute{2}.StringAttribute.name = IFC_PredefinedType
      SET_TO genericAttribute{2}.StringAttribute.value = @Value(PredefinedType)
    -> AttributeKeeper_2
    -> AttributeRenamer_1
AttributeCreator_14
    ATTR_TABLE:
      SET_TO genericAttribute{2}.StringAttribute.name =  IFC_ObjectType
      SET_TO genericAttribute{2}.StringAttribute.value = @Value(ObjectType)
    -> AttributeKeeper_2
    -> AttributeRenamer_1
AttributeRenamer_1
    ATTR_TABLE:
      RENAME_SET_DEFAULT Name > gml_name{0}
      RENAME_SET_DEFAULT gml_id_BCE > gml_id
    -> GeometryExtractor_1
GeometryExtractor_1
    ATTR = lod3Solid
    KIND_LONG = GML v3.2.1
    OMIT_NAMESPACES_DISPLAY = No
    PREFER_POLYGON_OVER_SURFACE = No
    REMOVE_GEOMETRY = No
    -> GeometryPropertySetter_1
GeometryPropertySetter_1
    OVERWRITE_CHOICE = Yes
    REMOVE_ATTRIBUTE = No
    SETTYPE_PARAM = Traits From Attributes
    SRC_ATTRS = citygml_lod_name
    SET -> FeatureMerger_1 [REQUESTOR]
AttributeKeeper_2
    CREATE_BULK_MODE_FEATURES = No
    KEEP_ATTRS = gml_id_BCE,gml_id_BCE_ref

Bookmark: BuidingInstallation
AttributeCreator_16
    ATTR_TABLE = SET_TO function{0} = 1060
    -> FeatureMerger_15 [SUPPLIER]
    -> AttributeKeeper_10
AttributeCreator_15
    ATTR_TABLE:
      SET_TO genericAttribute{2}.StringAttribute.name = IFC_PredefinedType
      SET_TO genericAttribute{2}.StringAttribute.value = @Value(PredefinedType)
      SET_TO function{0} = 1070
    -> FeatureMerger_15 [SUPPLIER]
FeatureMerger_15
    ATTR_ACCUM_MODE = Merge Supplier
    ATTR_CONFLICT_RES = Use Requestor
    IGNORE_NULLS = No
    JOIN_KEYS = @Value(GlobalId) @Value(GlobalId) AUTO
    MERGE_TYPE = Attributes Only
    PROCESS_DUPS = NO
    REJECT_NULL_MISSING_KEYS = No
    SUPPLIERS_FIRST = No
    MERGED -> AttributeCreator_3
AttributeCreator_3
    ATTR_TABLE:
      SET_TO citygml_lod_name = lod3MultiSurface
      SET_TO citygml_feature_role = buildingInstallation
      SET_TO gml_id = id_@UUID()
      SET_TO genericAttribute{0}.StringAttribute.name = IFC_GlobalId
      SET_TO genericAttribute{0}.StringAttribute.value = @Value(GlobalId)
      SET_TO genericAttribute{1}.StringAttribute.name = IFC_Tag
      SET_TO genericAttribute{1}.StringAttribute.value = @Value(Tag)
      SET_TO class = 1010
    -> AttributeRenamer_4
AttributeRenamer_4
    ATTR_TABLE:
      RENAME_SET_DEFAULT Name > gml_name{0}
      RENAME_SET_DEFAULT PredefinedType > gml_name{0}
    -> ConvertGeometry_2
ConvertGeometry_2
    IFC_UNIQUE_ID = @Value(gml_id)
    -> GeometryExtractor_2
GeometryExtractor_2
    ATTR = lod3MultiSurface
    KIND_LONG = GML v3.2.1
    OMIT_NAMESPACES_DISPLAY = No
    PREFER_POLYGON_OVER_SURFACE = No
    REMOVE_GEOMETRY = No
    -> GeometryPropertySetter_2
GeometryPropertySetter_2
    OVERWRITE_CHOICE = Yes
    REMOVE_ATTRIBUTE = No
    SETTYPE_PARAM = Traits From Attributes
    SRC_ATTRS = citygml_lod_name

Bookmark: BuildingRoom
AttributeKeeper_10
    CREATE_BULK_MODE_FEATURES = No
    KEEP_ATTRS = GlobalId
    -> FeatureMerger_17 [REQUESTOR]
FeatureMerger_17
    ATTR_ACCUM_MODE = Merge Supplier
    ATTR_CONFLICT_RES = Use Requestor
    IGNORE_NULLS = No
    JOIN_KEYS = @Value(GlobalId) @Value(GlobalId) AUTO
    MERGE_TYPE = Attributes Only
    PROCESS_DUPS = NO
    REJECT_NULL_MISSING_KEYS = No
    SUPPLIERS_FIRST = No
    MERGED -> AttributeCreator_2
AttributeCreator_2
    ATTR_TABLE:
      SET_TO citygml_lod_name = lod3Solid
      SET_TO citygml_feature_role = buildingRoom
      SET_TO gml_id = id_@UUID()
      SET_TO genericAttribute{0}.StringAttribute.name = IFC_GlobalId
      SET_TO genericAttribute{0}.StringAttribute.value = @Value(GlobalId)
      SET_TO genericAttribute{1}.StringAttribute.name = IFC_CompositionType
      SET_TO genericAttribute{1}.StringAttribute.value = @Value(CompositionType)
      SET_TO class = 1000
    -> AttributeRenamer_2
AttributeRenamer_2
    ATTR_TABLE = RENAME_SET_DEFAULT LongName > gml_name{0}
    -> GeometryExtractor_5
GeometryExtractor_5
    ATTR = lod3Solid
    KIND_LONG = GML v3.2.1
    OMIT_NAMESPACES_DISPLAY = No
    PREFER_POLYGON_OVER_SURFACE = No
    REMOVE_GEOMETRY = No
    -> GeometryPropertySetter_5
GeometryPropertySetter_5
    OVERWRITE_CHOICE = Yes
    REMOVE_ATTRIBUTE = No
    SETTYPE_PARAM = Traits From Attributes
    SRC_ATTRS = citygml_lod_name
    SET -> FeatureMerger_1 [REQUESTOR]
    SET -> GeometryRemover

Bookmark: References Storey - Room
GeometryRemover
    REMOVE_COORDSYS = No
    -> AttributeKeeper
AttributeKeeper
    CREATE_BULK_MODE_FEATURES = No
    KEEP_ATTRS = ifc_parent_id,gml_id
    -> AttributeCreator_8
AttributeCreator_8
    ATTR_TABLE:
      SET_TO xlink_href = #@Value(gml_id)
      SET_TO element_parent_id = @Value(ifc_parent_id)
    -> FeatureMerger [SUPPLIER]
FeatureMerger
    ATTR_ACCUM_MODE = Merge Supplier
    ATTR_CONFLICT_RES = Use Requestor
    IGNORE_NULLS = No
    JOIN_KEYS = @Value(gml_id_storey_ref) @Value(element_parent_id) AUTO
    LIST_ATTRS_TO_INCLUDE = xlink_href
    LIST_NAME = buildingRoom
    MERGE_TYPE = Attributes Only
    PROCESS_DUPS = NO
    REJECT_NULL_MISSING_KEYS = No
    SUPPLIERS_FIRST = No
    MERGED -> FeatureMerger_1 [REQUESTOR]
    UNMERGED_REQUESTOR -> FeatureMerger_1 [REQUESTOR]

FME custom transformer ConvertGeometry

Parameters:
- IFC_UNIQUE_ID = @Value(ifc_unique_id)   # Ifc Unique Id

Input (input)
    -> GeometryPartExtractor_3
GeometryPartExtractor_3
    GQUERY:
      for $geom in //geometry
      where $geom/@fme_geometry_type = ('IFMEBox', 'IFMEExtrusion', 'IFMEBRepSolid', 'IFMEMultiSolid')
      return number($geom/@fme_id)
    EXTRACTED -> GeometryCoercer_3
GeometryCoercer_3
    GQUERY:
      for $geom in //geometry
      where $geom/@fme_geometry_type = 'IFMEExtrusion'
      or $geom/@fme_geometry_type = 'IFMEBRepSolid'
      or $geom/@fme_geometry_type = 'IFMEBox'
      or $geom/@fme_geometry_type = 'IFMEMultiSolid'
      return number($geom/@fme_id)
    KIND = fme_composite_surface
    COERCED -> Deaggregator
Deaggregator
    EXPLODE_INSTANCES = Yes
    GEOM_NAME_FIELD = _geometry_name
    LIST_ATTR_MODE_LOOKUP = LEAN
    MODE = Flatten All Levels
    SPLIT_COMPOSITES = No
    DEAGGREGATED -> Aggregator
Aggregator
    ACCUM_ATTRS_NAME = Merge Incoming Attributes
    AGGREGATE_TYPE = Homogeneous Collection (If Possible)
    GROUP_BY = ifc_unique_id
    MODE = Geometry - Assemble One Level
    ORDERED = No
    SEP = ,
    AGGREGATE -> GeometryRefiner_3
GeometryRefiner_3
    -> Output (output)
Output (output)

FME custom transformer ConvertGeometryLanduse

Parameters:
- IFC_UNIQUE_ID = @Value(ifc_unique_id)   # Ifc Unique Id

Input (input)
    -> GeometryPartExtractor_3
GeometryPartExtractor_3
    GQUERY:
      for $geom in //geometry
      where $geom/@fme_geometry_type = ('IFMEBox', 'IFMEBRepSolid', 'IFMEAggregate')
      return number($geom/@fme_id)
    EXTRACTED -> GeometryCoercer_3
GeometryCoercer_3
    GQUERY:
      for $geom in //geometry
      where $geom/@fme_geometry_type = 'IFMEExtrusion'
      or $geom/@fme_geometry_type = 'IFMEBRepSolid'
      or $geom/@fme_geometry_type = 'IFMEBox'
      or $geom/@fme_geometry_type = 'IFMEMultiSolid'
      return number($geom/@fme_id)
    KIND = fme_composite_surface
    COERCED -> Deaggregator
Deaggregator
    EXPLODE_INSTANCES = Yes
    GEOM_NAME_FIELD = _geometry_name
    LIST_ATTR_MODE_LOOKUP = LEAN
    MODE = Flatten All Levels
    SPLIT_COMPOSITES = Yes
    DEAGGREGATED -> GeometryCoercer
GeometryCoercer
    GQUERY:
      for $geom in //geometry
      where $geom/@fme_geometry_type != 'IFMENull'
      return number($geom/@fme_id)
    KIND = fme_polygon
    COERCED -> OrientationExtractor
OrientationExtractor
    ORIENTATION = _orientation
    -> TestFilter
TestFilter
    DEFAULT_VALUE = <UNFILTERED>
    TEST_LIST = "BOOL_OP,OR,COMPOSITE_TEST,""""""<Unused>"""""",TEST_CLAUSE,TEST @Value(_orientation) = left_hand_rule",@Value(_orientation) = Left Hand Rule
    @Value(_orientation) = Left Hand Rule -> Aggregator
Aggregator
    ACCUM_ATTRS_NAME = Use Attributes From One Feature
    AGGREGATE_TYPE = Homogeneous Collection (If Possible)
    MODE = Geometry - Assemble One Level
    ORDERED = No
    SEP = ,
    AGGREGATE -> GeometryRefiner_3
GeometryRefiner_3
    -> Output (output)
Output (output)
